#usage "<b>Change lib text sizes</b>\n"
       "<p>This script loops through all packages in a library and changes the text size and ratio to new user specified values. "
       "<author>Author: Cameron Nicks, Phase IV Engineering. Modified from bobstarr</author>"

string ulp_path = "";
string script_change = "";

int Result = 0;
string grid = "GRID MIL FINEST;\n";

// new text sizes/ratios in mils

real tPlaceSize     = 40;
int  tPlaceRatio    = 18;

real tNamesSize     = 40;
int  tNamesRatio    = 18;

real tValuesSize    = 32;
int  tValuesRatio   = 10;

real SchNamesSize   = 100;
int  SchNamesRatio  = 12;

real SchValuesSize  = 70;
int  SchValuesRatio = 10;

void DoPackage(UL_PACKAGE P) {

    real dx, dy;

    P.texts(T) {
        dx = u2mil(T.x);
        dy = u2mil(T.y);
        if (T.layer == 21) {
            // Change tPlace layer text
	    printf("CHANGE SIZE %.3f (%.3f %.3f);\n", tPlaceSize, dx, dy);
            printf("CHANGE RATIO %d (%.3f %.3f);\n", tPlaceRatio, dx, dy);
	    printf("CHANGE FONT VECTOR (%.3f %.3f);\n", dx, dy);
        } else if (T.layer == 25) {
            // Change tNames layer text
	    printf("CHANGE SIZE %.3f (%.3f %.3f);\n", tNamesSize, dx, dy);
            printf("CHANGE RATIO %d (%.3f %.3f);\n", tNamesRatio, dx, dy);
	    printf("CHANGE FONT VECTOR (%.3f %.3f);\n", dx, dy);
        } else if (T.layer == 27) {
            // Change tValues layer text
	    printf("CHANGE SIZE %.3f (%.3f %.3f);\n", tValuesSize, dx, dy);
            printf("CHANGE RATIO %d (%.3f %.3f);\n", tValuesRatio, dx, dy);
	    printf("CHANGE FONT VECTOR (%.3f %.3f);\n", dx, dy);
        }
    }
}

void DoSymbol(UL_SYMBOL S) {

    real dx, dy;

    S.texts(T) {
        dx = u2mil(T.x);
        dy = u2mil(T.y);
        if (T.layer == 95) {
            // Change schematic names layer text
	    printf("CHANGE SIZE %.3f (%.3f %.3f);\n", SchNamesSize, dx, dy);
            printf("CHANGE RATIO %d (%.3f %.3f);\n", SchNamesRatio, dx, dy);
	    printf("CHANGE FONT VECTOR (%.3f %.3f);\n", dx, dy);
        } else if (T.layer == 96) {
            // Change schematic values layer text
	    printf("CHANGE SIZE %.3f (%.3f %.3f);\n", SchValuesSize, dx, dy);
            printf("CHANGE RATIO %d (%.3f %.3f);\n", SchValuesRatio, dx, dy);
	    printf("CHANGE FONT VECTOR (%.3f %.3f);\n", dx, dy);
        }                
    }
}


void menue(void) {
   int err = 0;
   int newWidth;
   int minLimit = 0;
   int maxLimit = 0;

   dlgDialog("Change All Text Sizes/Ratios") {
      //dlgStretch(1);
         dlgGroup("tPlace Text") {
            dlgHBoxLayout {   dlgLabel("New size (2-100 mils) :\t"); dlgRealEdit(tPlaceSize, 10.0, 100.0);   }
            dlgHBoxLayout {   dlgLabel("New ratio  (8-20%) :\t"); dlgIntEdit(tPlaceRatio, 8, 20);   }
         }
         dlgGroup("tNames Text") {
            dlgHBoxLayout {   dlgLabel("New size (2-100 mils) :\t"); dlgRealEdit(tNamesSize, 10.0, 100.0);   }
            dlgHBoxLayout {   dlgLabel("New ratio  (8-20%) :\t"); dlgIntEdit(tNamesRatio, 8, 20);   }
         }
         dlgGroup("tValues Text") {
            dlgHBoxLayout {   dlgLabel("New size (2-100 mils) :\t"); dlgRealEdit(tValuesSize, 10.0, 100.0);   }
            dlgHBoxLayout {   dlgLabel("New ratio (8-20%) :\t"); dlgIntEdit(tValuesRatio, 8, 20);   }
         }

	//Schematic text
	dlgGroup("Sch Names Text") {
            dlgHBoxLayout {   dlgLabel("New size (2-100 mils) :\t"); dlgRealEdit(SchNamesSize, 10.0, 100.0);   }
            dlgHBoxLayout {   dlgLabel("New ratio  (8-20%) :\t"); dlgIntEdit(SchNamesRatio, 8, 20);   }
         }
         dlgGroup("Sch Values Text") {
            dlgHBoxLayout {   dlgLabel("New size (2-100 mils) :\t"); dlgRealEdit(SchValuesSize, 10.0, 100.0);   }
            dlgHBoxLayout {   dlgLabel("New ratio (8-20%) :\t"); dlgIntEdit(SchValuesRatio, 8, 20);   }
         }
      //dlgStretch(1);
      dlgPushButton("+&OK") { dlgAccept(); return; }
      dlgPushButton("-&Cancel") { dlgReject(); exit (0);}
   };
}

if (library) {
   char bkslash = '/';
   int pos = strrchr(argv[0], bkslash);
   if (pos >= 0) {
      ulp_path = strsub(argv[0], 0, pos + 1);
   }
   int n = 0;
   library(L) {
   int posb = strrchr(argv[0], bkslash);
   if (posb >= 0) {
      ulp_path = strsub(argv[0], 0, posb + 1);
   }

   menue();

   script_change = filesetext(L.name, "~~~.scr");

   output(script_change, "wtD") {

      int firstf = 1;
      L.packages(P) {
         printf("EDIT %s.PAC;\n", P.name);
      	 printf("DISPLAY NONE 21 25 27 51;\n");
         if (firstf) {
           printf("%s",grid);
           firstf = 0;
         }

         DoPackage(P);
      }

      firstf = 1;
      L.symbols(S) {
         printf("EDIT %s.SYM;\n", S.name);
      	 printf("DISPLAY NONE 95 96;\n");
         if (firstf) {
           printf("%s",grid);
           firstf = 0;
         }

         DoSymbol(S);
      }

      printf("GRID DEFAULT;\n");
      printf("DISPLAY All;\n");
   }
   }
  exit ("SCRIPT '" + script_change + "';\n"); // REMOVE " + script_change + ";\n");
} else {
   dlgMessageBox("\n*** Start this ULP in a Library ***\n");
   exit (0);
}
