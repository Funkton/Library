//////////////////////////////////////////////////////////////////////////////
//  This EAGLE User Language Program creates a comma separated
//  file with mount information for SMDs on top and bottom.
//  Syntax is as follows:
//  name, x-coord, y-coord, rotation, value, package, partno
//
// REVISION HISTORY:
// Rev 1.0 	Original ULP from Bob Starr repository https://github.com/robertstarr
//
// Rev 1.1 CN 03/01/17  Added attribute 'PARTNO' to output
//                      Moved THROUGH HOLE PARTS section into separate file.
//						Added Company, Contact, and Copyright information to file output.
//
// Rev 1.2 CN 10/13/17  Removed extra space before each csv value. Change - to . in file name.
//											Added removal based on Value= DNP
//											Added variant information to file
//
// Rev 1.3 CN 12/01/17  Added Type listing
//
////////////////////////////////////////////////////////////
//
// KNOWN BUGS:
// 						Commas in value move the cell over. Must enclose if comma found.
//
//////////////////////////////////////////////////////////////////////////////
//
// THIS PROGRAM IS PROVIDED AS IS AND WITHOUT WARRANTY OF ANY KIND,
// EXPRESSED OR IMPLIED. IF YOU DON'T LIKE IT, DON'T USE IT!
//
//////////////////////////////////////////////////////////////////////////////

#usage "<b>Data generation for mounting machines</b>\n"
       "<p>"
       "Generates one comma separated file listing top and bottom layer SMD "
       "which can be used with Advanced Assembly's mounting machines."
       "The x and y coordinates units are now based on current GRID settings"
       "The calculated value does not necessarily fit with the origin "
       "point of the part in the layout."
       "orignal author: support@cadsoft.de</author>"
       "<p>"
       "The syntax of the output data looks like this:"
       "<p>"
       "<tt>name, x-coord, y-coord, rotation, value, package, partno</tt>"
       "<p>"
       "<author>Author: lawcockc@onyxgaming.com</author>"
       "<p>"
       "<author>Modified by: Cameron Nicks, Phase IV Engineering, cnicks@phaseivengr.com</author>"
	   
    "<p>"

// Define strings
string Version = "Rev 1.3";
string Boardname;
string Company = "";
string Contact = "";
string Copyright = "Information contained within this file is confidential. Any reproduction in part or whole is strictly prohibited without written permission or as required by non-disclosure agreement.";

string CurrentVariant = variant();
string BomNum = "";

// Main
if (board) board(B)
{
	// Get some global attributes.
		B.attributes(A) {
			if (A.name == "BOMNO"){
				BomNum = A.value;
			}
		}
	
	Boardname = filename(B.name);
    // Get filename
    string fileName = dlgFileSave("Save File", filesetext(B.name, "-XY-SMD.csv"), "*.csv");
    if (fileName == "") exit(0);

    output(fileName)
    {
		printf ("Company:\n%s\n\n", Company);
		printf ("Contact:,%s\n\n", Contact);
		
		printf("Board:,%s \n", Boardname);
		printf("Variant:,%s%s \n\n", BomNum, CurrentVariant);
		printf ("Type: Surface Mount Components\n");
//		printf("%s;\n\n", EAGLE_SIGNATURE);

		

		//
        // PROCESS SURFACE MOUNT PARTS
        //
	  
        printf ("Layer: Top\n");
        //printf ("Report Origin: (0.0,0.0)\n");
        printf ("Unit: ");

        if (B.grid.unit == GRID_UNIT_MIC)
        {
            printf ("microns\n");
        }

        if (B.grid.unit == GRID_UNIT_MM)
        {
            printf ("mm\n");
        }

        if (B.grid.unit == GRID_UNIT_MIL)
        {
            printf ("mil\n");
        }

        if (B.grid.unit == GRID_UNIT_INCH)
        {
            printf ("inch\n");
        }

        //
        // PROCESS TOP SIDE SMD PARTS
        //

        printf ("\nRefDes,LocationX,LocationY,Rotation,Value,Package,Partno\n");

        B.elements(E) if (E.populate)
        {
            int wasSmd,
            xmax =-2147483648,
            xmin = 2147483647,
            ymax = xmax,
            ymin = xmin;

            wasSmd = 0;

            int bomDNP = 0;

            E.package.contacts(C)
            {
                if ((C.smd && C.smd.layer == 1))
                {
                    wasSmd = 1;
                    if (C.x > xmax) xmax = C.x;
                    if (C.y > ymax) ymax = C.y;
                    if (C.x < xmin) xmin = C.x;
                    if (C.y < ymin) ymin = C.y;
                }
            }

            // Check for DNP or BOM EXCLUDED PARTS
            E.attributes(A)
            {
                if (A.name == "BOM")
                {
                    // Exclude part from BOM?
                    if (A.value == "EXCLUDE")
                        bomDNP = 1;
                }
                else if (A.name == "DNP")
                {
                    // Exclude part from BOM?
                    if ((A.value == "T") || (A.value != "1"))
                        bomDNP = 1;
                }
								else if (A.name == "VALUE")
								{
									// Exclude part from BOM?
                    if (A.value == "DNP")
                        bomDNP = 1;
								}
            }

            if (wasSmd)
            {
                real x,y;

                switch (B.grid.unit)
                {
                    case GRID_UNIT_MIC:
                        x = u2mic ((xmin + xmax) / 2);
                        y = u2mic ((ymin + ymax) / 2);
                        break;
                    case GRID_UNIT_MIL:
                        x = u2mil ((xmin + xmax) / 2);
                        y = u2mil ((ymin + ymax) / 2);
                        break;
                    case GRID_UNIT_MM:
                        x = u2mm ((xmin + xmax) / 2);
                        y = u2mm ((ymin + ymax) / 2);
                        break;
                    case GRID_UNIT_INCH:
                        x = u2inch ((xmin + xmax) / 2);
                        y = u2inch ((ymin + ymax) / 2);
                        break;
                }

                string value = E.value, name = E.package.name, partno = E.attribute["PARTNO"];
                int index = 0;

                while ((index = strchr (value,' ',index)) >= 0)
                {
                    value[index] = '_';
                }

                index = 0;

                while ((index = strchr (name,' ',index)) >= 0)
                {
                    name[index] = '_';
                }
				
							index = 0;
				
							while ((index = strchr (partno,' ',index)) >= 0)
                {
                    partno[index] = '_';
                }

                //if (strlen (value) == 0) value = "none";
                //if (strlen (name) == 0) value = "none";
                //if (strlen (partno) == 0) value = "none";

							if (!bomDNP)
								{
	                printf("%s,%5.4f,%5.4f,%3.0f,%s,%s,%s\n",
	                    E.name, x, y,
	                    E.angle, value, name, partno);
								}
            }
        }

        printf ("\n\nLayer: Bottom\n");
        //printf ("Report Origin: (0.0,0.0)\n");
        printf ("Unit: ");

        if (B.grid.unit == GRID_UNIT_MIC)
        {
            printf ("microns\n");
        }

        if (B.grid.unit == GRID_UNIT_MM)
        {
            printf ("mm\n");
        }

        if (B.grid.unit == GRID_UNIT_MIL)
        {
            printf ("mil\n");
        }

        if (B.grid.unit == GRID_UNIT_INCH)
        {
            printf ("inch\n");
        }

        //
        // PROCESS BOTTOM SIDE SMD PARTS
        //

        printf ("\nRefDes, LocationX, LocationY, Rotation, Value, Package\n");

        B.elements(E) if (E.populate)
        {
            int wasSmd,
                 xmax =-2147483648,
                 xmin = 2147483647,
                 ymax = xmax,
                 ymin = xmin;

            wasSmd = 0;

            int bomDNP = 0;

            E.package.contacts(C)
            {
                if (C.smd && C.smd.layer == 16)
                {
                    wasSmd = 1;

                    if (C.x > xmax) xmax = C.x;
                    if (C.y > ymax) ymax = C.y;
                    if (C.x < xmin) xmin = C.x;
                    if (C.y < ymin) ymin = C.y;
                }
            }

            // Check for DNP or BOM EXCLUDED PARTS
            E.attributes(A)
            {
                if (A.name == "BOM")
                {
                    // Exclude part from BOM?
                    if (A.value == "EXCLUDE")
                        bomDNP = 1;
                }
                else if (A.name == "DNP")
                {
                    // Exclude part from BOM?
                    if ((A.value == "T") || (A.value != "1"))
                        bomDNP = 1;
                }
								else if (A.name == "VALUE")
								{
									// Exclude part from BOM?
                    if (A.value == "DNP")
                        bomDNP = 1;
								}
            }

            if (wasSmd)
            {
                real x,y;

                switch (B.grid.unit)
                {
                    case GRID_UNIT_MIC:
                        x = u2mic ((xmin + xmax) / 2);
                        y = u2mic ((ymin + ymax) / 2);
                        break;
                    case GRID_UNIT_MIL:
                        x = u2mil ((xmin + xmax) / 2);
                        y = u2mil ((ymin + ymax) / 2);
                        break;
                    case GRID_UNIT_MM:
                        x = u2mm ((xmin + xmax) / 2);
                        y = u2mm ((ymin + ymax) / 2);
                        break;
                    case GRID_UNIT_INCH:
                        x = u2inch ((xmin + xmax) / 2);
                        y = u2inch ((ymin + ymax) / 2);
                        break;
                }

                string value = E.value, name = E.package.name, partno = E.attribute["PARTNO"];
                int index = 0;

                while ((index = strchr (value,' ',index)) >= 0)
                {
                    value[index] = '_';
                }

                index = 0;

                while ((index = strchr (name,' ',index)) >= 0)
                {
                    name[index] = '_';
                }
				
				index = 0;
				
				while ((index = strchr (partno,' ',index)) >= 0)
                {
                    partno[index] = '_';
                }

                //if (strlen (value) == 0) value = "none";
                //if (strlen (name) == 0) value = "none";
                //if (strlen (partno) == 0) value = "none";

				if (!bomDNP)
				{
	                printf("%s,%5.4f,%5.4f,%3.0f,%s,%s,%s\n",
	                    E.name, x, y,
	                    E.angle, value, name, partno);
				}
            }
        }
		
		printf("\nSMD component position Data generated by %s %s at %s\n\n", filename(argv[0]), Version, t2string(time()));
		// List copyright information at bottom of file
		printf ("NOTICE: %s\n\n", Copyright);

    }
}
else
{
   dlgMessageBox("\n    Start this ULP in a Board    \n");
   exit (0);
}
