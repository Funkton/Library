#usage "<b>Add _1 Suffix to parts for panelization purposes. U1 -> U1_1</b><p>"
       "RUN PART-SUFFIX<br>"
       "<author>Author: cnicks@phaseivengr.com</author>";

// THIS PROGRAM IS PROVIDED AS IS AND WITHOUT WARRANTY OF ANY KIND,
// EXPRESSED OR IMPLIED.


string Version = "Version 0.1"; // check if schematic editor window open

string fileName;

string suffix = "1";

// ### Functions ###


/*
if (project.schematic) {
  dlgMessageBox(argv[0]+ "\n" + Version + "\nFirst close the schematic editor!", "OK");
  exit(-1);
}
*/

// ** MAIN **
if (board) {
  board(B) {
    fileName = filesetext(B.name, "-add-suffix.scr");
    int cntsig = 0;
    output(fileName, "wtD") {
      printf("# 'This file is generated by %s, exported from;\n", Version);
      printf("# '%s at %s;\n", fileName, t2string(time()));
      printf("# '%s;\n\n", EAGLE_SIGNATURE);
      B.elements(E) printf("NAME %s %s_%s \n", E.name, E.name, suffix);
    }
    exit ("SCRIPT '" + fileName + "';");
  }
}
else dlgMessageBox("Start this ULP in Board!", "OK");
