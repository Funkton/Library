string strtrim(string str) {
	string result = "";
	if (strlen(str) == 0) return "";
	int i = 0;
	while (str[i] && isspace(str[i])) {
		i++;
	}
	int s = i;
	i = strlen(str)-1;
	while (i>=0 && isspace(str[i])) {
		i--;
	}
	int e = i;
	if (e-s+1>0) return strsub(str,s,e-s+1);
	else return "";
}

if (package) package (P) {
	int i = strxstr(P.description, "Package generated by:");
	if (i>0) {
		string str = strsub(P.description, i);
		int e = strchr(str, '\n');
		str = strsub(P.description, i, e-i);
		string cell[];
		strsplit(cell,str, ':');
		str = strtrim(cell[1]);
		exit ("RUN '"+filedir(argv[0])+"ipc-wizard/"+str+"' EDIT;");
	}
}
