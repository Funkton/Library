#usage "en: Export IDF board\n"
			"Exports current board in Intermediate Data Format, Version 3.0\n"
			"The components are named using the package name defined in the Eagle library\n"
			"IDF_FAMILYNAME : If present, the IDF package name is overwritten by the attribute value\n"
			"IDF_PARTNUMBER : If present, the IDF part number is overwritten by the attribute value\n"
			"HEIGHT : Is used together with the keepout layer to define a simple extrusion model as fallback\n"
			"_IDF_IGNORE_ : If present, the component is not exported to IDF. Does not care about the value.\n" 
			"Usage: RUN export-idf.ulp\n"
			"Author: behner@zess.uni-siegen.de"
			"Author: reuter@zess.uni-siegen.de"

string boardFilename = "test.emn";
string libFilename = "test.emp";

real atan2(real y, real x) {
	if (x>0) {
		return atan(y/x);
	}
	if (x<0 && y>=0) {
		return (atan(y/x) + PI);
	}
	if (x<0 && y<0) {
		return (atan(y/x) - PI);
	}
	if (x==0 && y>0) {
		return (PI/2);
	}
	if (x==0 && y<0) {
		return -(PI/2);
	}
	if (x==0 && y==0) {
		return 0;
	}
}

int isAttribute(UL_ELEMENT el, string attributeName){
	el.attributes(att){
		if (att.name == attributeName)
			return 1;
	}
	return 0;
}

string strrep(string s, char old, char new) {
    int index=0;
    while (index!=-1) {
        index=strchr(s,old,index);
        if (index!=-1) {
            s[index]=new;
        }
    }
    return s;
}

void createLibFileHeader() {
	output(libFilename) {
		printf(".HEADER\n");
		printf("LIBRARY_FILE 3.0 ""EAGLE IDF Exporter"" %s 1\n", t2string(time(), "yyyy/MM/dd.hh:mm:ss"));
		printf(".END_HEADER\n");
	}
}

void createBoardFileHeader() {
	output(boardFilename) {
		printf(".HEADER\n");
		printf("BOARD_FILE 3.0 ""EAGLE IDF Exporter"" %s 1\n", t2string(time(), "yyyy/MM/dd.hh:mm:ss"));
		printf("%s MM\n", strrep(filesetext(filename(boardFilename), ""), ' ', '_'));
		printf(".END_HEADER\n");
	}
}

void createDrilledHolesSection() {
	output(boardFilename, "at") {
		printf(".DRILLED_HOLES\n");
		board(B) {
			/* Create Board Holes */
			B.holes(H) printf("%.3f %.3f %.3f NPTH BOARD MTG ECAD\n",u2mm(H.drill), u2mm(H.x), u2mm(H.y));

			/* Create Vias */
			B.signals(S) S.vias(V) printf("%.3f %.3f %.3f PTH BOARD VIA ECAD\n",u2mm(V.drill), u2mm(V.x), u2mm(V.y));

			/* Create Component Pins/Holes */
			B.elements(E) {
				if (!isAttribute(E,"_IDF_IGNORE_")){
					string referenceDesignator = E.name;
					E.package.holes(H) printf("%.3f %.3f %.3f NPTH %s MTG ECAD\n",u2mm(H.drill), u2mm(H.x), u2mm(H.y), referenceDesignator);
					E.package.contacts(C) {
						if (C.pad) {
							printf("%.3f %.3f %.3f PTH %s PIN ECAD\n",u2mm(C.pad.drill), u2mm(C.pad.x), u2mm(C.pad.y), referenceDesignator);
						}
					}
				}
			}
		}
		printf(".END_DRILLED_HOLES\n");
	}
}

void createComponentPlacementSection() {
	output(boardFilename, "at") {
		printf(".PLACEMENT\n");
		board(B) B.elements(E) {
			if (!isAttribute(E,"_IDF_IGNORE_")){
				string packageName = E.attribute["IDF_FAMILYNAME"];
				if (packageName=="")
					packageName = E.package.name;
				string partNumber = E.attribute["IDF_PARTNUMBER"];
				if (partNumber=="")
					partNumber = E.package.name;
				string referenceDesignator = E.name;
				printf("%s %s %s\n",packageName, partNumber, referenceDesignator);
				real mountingOffset = 0;
				string placementSide = "TOP";
				if (E.mirror)
					placementSide = "BOTTOM";
				printf("%.3f %.3f %.3f %0.3f %s ECAD\n",u2mm(E.x), u2mm(E.y), mountingOffset, E.angle, placementSide);
			}
		}
		printf(".END_PLACEMENT\n");
	}
}

string libraryPackageName[];
string libraryPartNumber[];
int numLibraryExported = 0;
void createElectricalComponentSection() {
	output(libFilename, "at") {
		board(B) B.elements(E) {
			if (!isAttribute(E,"_IDF_IGNORE_")){
				string packageName = E.attribute["IDF_FAMILYNAME"];
				if (packageName == "")
					packageName = E.package.name;
				string partNumber = E.attribute["IDF_PARTNUMBER"];
				if (partNumber == "")
					partNumber = E.package.name;
				int notExported = 1;
				for (int i=0; i < numLibraryExported; i++)
					if ((libraryPackageName[i] == packageName) && (libraryPartNumber[i] == partNumber)){
						notExported = 0;
						break;
					}
				if (notExported){
					printf(".ELECTRICAL\n");
					libraryPackageName[numLibraryExported] = packageName;
					libraryPartNumber[numLibraryExported] = partNumber;
					numLibraryExported++;
					
					string height_att = E.attribute["HEIGHT"];
					real height = 1;
					if (height_att != "")
							height = strtod(height_att);
					printf("%s %s MM %.3f\n",packageName, partNumber, height);
					B.libraries(L)
						if (L.name == E.package.library)
							L.packages(P) 
								if (P.name == E.package.name) {
									int leftPointX = INT_MAX;
									int leftPointY = INT_MAX;
									P.wires(W) {
										if (W.layer == LAYER_TKEEPOUT) {
											if (W.x1 < leftPointX) {
												leftPointX = W.x1;
												leftPointY = W.y1;
											} else if ((W.x1 == leftPointX) && (W.y1 < leftPointY))
												leftPointY = W.y1;
											if (W.x2 < leftPointX) {
												leftPointX = W.x2;
												leftPointY = W.y2;
											} else if ((W.x2 == leftPointX) && (W.y2 < leftPointY))
												leftPointY = W.y2;
										}
									}
									int cx = leftPointX;
									int cy = leftPointY;
									
									int lx = cx;
									int ly = cy;
									
									int xi[];
									int yi[];
									int idx = 0;
									
									P.wires(W) {
										if (W.layer == LAYER_TKEEPOUT) {
											if ((W.x1 == cx && W.y1 == cy) && !(W.x2 == lx && W.y2 == ly)) {
												xi[idx] = W.x2;
												yi[idx++] = W.y2;
											} else if ((W.x2 == cx && W.y2 == cy) && !(W.x1 == lx && W.y1 == ly)) {
												xi[idx] = W.x1;
												yi[idx++] = W.y1;
											}
										}
									}
									int cp = 0;
									if (idx==2) {
										cp = (xi[0]*yi[1]-xi[1]*yi[0]);
									} // else error
									real cc;
									printf("%d %.3f %.3f %.3f\n",cp<0, u2mm(cx), u2mm(cy), 0.0);
									do {
										int found = 0;
										P.wires(W) {
											if (W.layer == LAYER_TKEEPOUT) {
												if ((W.x1 == cx && W.y1 == cy) && !(W.x2 == lx && W.y2 == ly) && (!found)) {
													lx = cx;
													ly = cy;
													cx = W.x2;
													cy = W.y2;
													cc = W.curve;
													found = 1;
												} else if ((W.x2 == cx && W.y2 == cy) && !(W.x1 == lx && W.y1 == ly) && (!found)) {
													lx = cx;
													ly = cy;
													cx = W.x1;
													cy = W.y1;
													cc = -W.curve;
													found = 1;
												}
											}
										}
										if (found)
											printf("%d %.3f %.3f %.3f\n",cp<0, u2mm(cx), u2mm(cy), cc);
										// else error
									} while (cx != leftPointX || cy != leftPointY);
								}
					//printf("%.3f %.3f %.3f %0.3f %s ECAD\n",u2mm(E.x), u2mm(E.y), mountingOffset, E.angle, placementSide);
					printf(".END_ELECTRICAL\n");
				}
			}
		}
	}
}

real getBoardThickness() {
	board(B) {
		string xmlText;
		int nChars = fileread(xmlText, B.name);
		string drParams[];
		int nRules = xmlelements(drParams, xmlText, "eagle/drawing/board/designrules/param");
		string layerSetup;
		string mtCopper[];
		string mtIsolate[];
		for (int i = 0; i < nRules; i++) {
			string ruleName = xmlattribute(drParams[i], "param", "name");
			if (ruleName == "layerSetup")
				layerSetup = xmlattribute(drParams[i], "param", "value");
			if (ruleName == "mtCopper")
				int numMtCopper = strsplit(mtCopper, xmlattribute(drParams[i], "param", "value"), ' ');
			if (ruleName == "mtIsolate")
				int numMtIsolate = strsplit(mtIsolate, xmlattribute(drParams[i], "param", "value"), ' ');
		}
		layerSetup = strrep(layerSetup, '(', ' ');
		layerSetup = strrep(layerSetup, ')', ' ');
		layerSetup = strrep(layerSetup, '+', '*');
		string usedLayers[];
		int nLayer = strsplit(usedLayers, layerSetup, '*');
		real boardThickness = 0;
		for (i = 0; i < nLayer-1; i++)
			boardThickness += strtod(mtIsolate[i]);
		for (i = 0; i < nLayer; i++)
			boardThickness += strtod(mtCopper[strtol(usedLayers[i])-1]);
		return boardThickness;
	}
}

int usedBoardWireSegments[];

string followBoardOutlineLoop(int loopId, int ox, int oy, int dir) {
	string outStr = "";
	string tmp = "";
	int firstRun = 1;
	
	int cx = ox;
	int cy = oy;
	int lx = cx;
	int ly = cy;
	real cc = 0;

	int x[];
	int y[];
	real c[];
	int wid[];

	while (cx != ox || cy != oy || firstRun == 1) {
		sprintf(outStr,"%s%d %.3f %.3f %.3f\n", outStr, loopId, u2mm(cx), u2mm(cy), cc);
		int idx = 0;
		int currentSegment = 0;
		board(B) {
			B.wires(W) {
				if (W.layer == LAYER_DIMENSION) {
					if (usedBoardWireSegments[currentSegment] == 0) {
						if ((W.x1 == cx && W.y1 == cy) && !(W.x2 == lx && W.y2 == ly)) {
							wid[idx] = currentSegment;
							c[idx] = W.curve;
							x[idx] = W.x2;
							y[idx++] = W.y2;
						}
						if ((W.x2 == cx && W.y2 == cy) && !(W.x1 == lx && W.y1 == ly)) {
							wid[idx] = currentSegment;
							c[idx] = -W.curve;
							x[idx] = W.x1;
							y[idx++] = W.y1;
						}
					}
					currentSegment++;
				}
			}
		}
		
		if (idx == 0) {
			return "";
		}
		
		lx = cx;
		ly = cy;
		
		if (firstRun == 1) {
			int angle[];
			for (int i = 0; i < idx; i++) {
				angle[i] = atan2((y[i]-cy),(x[i]-cx));
			}
			int sidx[];
			sort(idx,sidx,angle);
			if (dir == 0) {
				cx = x[sidx[0]];
				cy = y[sidx[0]];
				cc = c[sidx[0]];
				usedBoardWireSegments[wid[sidx[0]]] = 1;
			} else {
				cx = x[sidx[idx-1]];
				cy = y[sidx[idx-1]];
				cc = c[sidx[idx-1]];
				usedBoardWireSegments[wid[sidx[idx-1]]] = 1;
			}
			
		} else {
			cx = x[0];
			cy = y[0];
			cc = c[0];
			usedBoardWireSegments[wid[0]] = 1;
		}
		
		firstRun = 0;
	}
	
	sprintf(outStr,"%s%d %.3f %.3f %.3f\n", outStr, loopId, u2mm(cx), u2mm(cy), cc);
	
	return outStr;
}

void createBoardOutline() {
	int x[];
	int y[];
	int wireId[];
	
	int currentSegment = 0;
	int currentPoint = 0;
	int loopCount = 0;
	output(boardFilename, "at") {
		printf(".BOARD_OUTLINE ECAD\n");
		printf("%.3f\n",getBoardThickness());
		do {
			
			currentSegment = 0;
			currentPoint = 0;
			board(B) {
				B.wires(W) {
					if (W.layer == LAYER_DIMENSION) {
						if (usedBoardWireSegments[currentSegment] == 0) {
							x[currentPoint] = W.x1;
							y[currentPoint] = W.y1;

							x[currentPoint] = W.x2;
							y[currentPoint++] = W.y2;
						}
						currentSegment++;
					}
				}
			}
			int idx[];
			
			if (currentPoint>0) {
				sort(currentPoint, idx, x, y, wireId);
				printf(followBoardOutlineLoop(loopCount,x[idx[0]],y[idx[0]], loopCount));
			}
			loopCount++;
		} while (currentPoint>0);
		printf(".END_BOARD_OUTLINE\n");
	}
	
}

void createTraceOutline() {
	int segmentNumber = 0;
	output(boardFilename, "at") {
		board(B) 
			B.signals(S) 
				S.wires(W) {
					if (W.layer == LAYER_TOP || W.layer == LAYER_BOTTOM) {
						string layer = "TOP";
						if (W.layer == LAYER_BOTTOM) {
							layer = "BOTTOM";
						}
						real angle = atan2(W.y2-W.y1, W.x2-W.x1);
						printf(".OTHER_OUTLINE ECAD\n");
						printf("trace_segment_%d %.3f %s\n",segmentNumber, 0.035, layer);
						printf("0 %.3f %.3f 0.000\n", u2mm(W.x1) + u2mm(W.width)/2*cos(angle - PI/2 - W.curve/180*PI/2), u2mm(W.y1) + u2mm(W.width)/2*sin(angle - PI/2 - W.curve/180*PI/2));
						printf("0 %.3f %.3f %.3f\n", u2mm(W.x2) + u2mm(W.width)/2*cos(angle - PI/2 + W.curve/180*PI/2), u2mm(W.y2) + u2mm(W.width)/2*sin(angle - PI/2 + W.curve/180*PI/2), W.curve);
						printf("0 %.3f %.3f 180.000\n", u2mm(W.x2) + u2mm(W.width)/2*cos(angle + PI/2 + W.curve/180*PI/2), u2mm(W.y2) + u2mm(W.width)/2*sin(angle + PI/2 + W.curve/180*PI/2));
						printf("0 %.3f %.3f %.3f\n", u2mm(W.x1) + u2mm(W.width)/2*cos(angle + PI/2 - W.curve/180*PI/2), u2mm(W.y1) + u2mm(W.width)/2*sin(angle + PI/2 - W.curve/180*PI/2), -W.curve);
						printf("0 %.3f %.3f 180.000\n", u2mm(W.x1) + u2mm(W.width)/2*cos(angle - PI/2 - W.curve/180*PI/2), u2mm(W.y1) + u2mm(W.width)/2*sin(angle - PI/2 - W.curve/180*PI/2));
						printf(".END_OTHER_OUTLINE\n");
						segmentNumber++;
					}
				}
		
	}
}
if (board) {
	board(B) {
		boardFilename = filesetext(B.name, ".emn");
		libFilename = filesetext(B.name, ".emp");

		createBoardFileHeader();
		createBoardOutline();
		//createTraceOutline();
		createDrilledHolesSection();
		createComponentPlacementSection();
		
		createLibFileHeader();
		createElectricalComponentSection();
	}
} else {
	dlgMessageBox(":Please run ulp in board");
}
