//QFP	Quad Flat Pack	Microcontroller, Micropocessor ...
//<p>This will allow you to generate QFP/TQFP packages</p><br><center><img width=256 src="ipc-wizard/qfp-01.png"></center>

#include "common.h"

//Wizard Description
wizardName = "Quad Flat Package";
wizardImage = "qfp-01.png";
wizardDescription = "<img src=\"qfp-02.png\">";

string materialConditionStr[] = {"L","N","M"};
string materialConditionLongStr[] = {"Least","Nominal","Most"};


// UI Parameter Elements
addParameterInt("nD","Number of Pins (ND)", 0);
addParameterInt("nE","Number of Pins (NE)", 0);
addParameterHeader("Overall Dimensions");
	addParameterMinMax("A", "Height (A)", 0, 0);
	addParameterMinMax("D", "Length (D)", 0, 0);
	addParameterMinMax("E", "Width (E)", 0, 0);
	
	
addParameterHeader("Body Dimensions");
	addParameterMinMax("D1", "Length (D1)", 0, 0);
	addParameterMinMax("E1", "Width (E1)", 0, 0);
	
addParameterHeader("Pin Dimensions");
	addParameterMinMax("b", "Pin Width (b)", 0, 0);
	addParameterMinMax("L", "Pin Length (L)", 0, 0);
	addParameterReal("e", "Pitch (e)", 0);
	
addParameterExposedPad(0,0,0,0,0,100,0.5);
	
int debugRet = 0;

runWizard();

int k = 0;

int materialCondition = getParameterListBox("materialCondition");

real Dmin = getParameterMin("D");
real Dmax = getParameterMax("D");

real Emin = getParameterMin("E");
real Emax = getParameterMax("E");

real Amin = getParameterMin("A");
real Amax = getParameterMax("A");

real D1min = getParameterMin("D1");
real D1max = getParameterMax("D1");

real E1min = getParameterMin("E1");
real E1max = getParameterMax("E1");

real Lmin = getParameterMin("L");
real Lmax = getParameterMax("L");

real bmin = getParameterMin("b");
real bmax = getParameterMax("b");

real pitch = getParameterReal("e");
real nE = getParameterInt("nE");
real nD = getParameterInt("nD");

string pitchCode = "PMAX";
if (pitch <= 1.00) pitchCode = "P100";
if (pitch <= 0.80) pitchCode = "P80";
if (pitch <= 0.65) pitchCode = "P65";
if (pitch <= 0.50) pitchCode = "P50";
if (pitch <= 0.40) pitchCode = "P40";

string index = pitchCode + materialConditionStr[materialCondition];



string path = filedir(argv[0]);
string tableContent[];
fileread(tableContent, path + "/qfp.data");
real Jt = strtod(lookup(tableContent, index, "Jtoe"));
real Jh = strtod(lookup(tableContent, index, "Jheel"));
real Js = strtod(lookup(tableContent, index, "Jside"));

// Draw Pads
real Zmax = calcZmax(Emin, Emax,Jt);
real Gmin = calcGmin(Emin, Emax, Lmin, Lmax, Jh);
real Xmax = calcXmax(bmin, bmax, Js);

real padSizeRoundOff = getLibraryParameterValueReal("padSizeRoundOff");
real padPlaceRoundOff = getLibraryParameterValueReal("padPlaceRoundOff");

real dx = ipcCeil((Zmax-Gmin)/2.0, padSizeRoundOff);
real dy = ipcCeil(Xmax,padSizeRoundOff);
real dpos = ipcRound(Zmax/2.0-dx/2.0, padPlaceRoundOff);

real offset = (pitch*(nD-1))/2;
int pinNumber = 1;
string pinName;
beginSmd(dx, dy);
	orientation(-90);
	for (k = 0; k < nD; k++) {
		sprintf(pinName, "%d", pinNumber);
		name(pinName);
		position(ipcRound(-offset+k*pitch,padPlaceRoundOff),-dpos);
		pinNumber++;
	}
	orientation(90);
	pinNumber = pinNumber + nE;
	for (k = 0; k < nD; k++) {
		sprintf(pinName, "%d", pinNumber);
		name(pinName);
		position(ipcRound(offset-k*pitch,padPlaceRoundOff), dpos);
		pinNumber++;
	}

end();

real Zmax2 = calcZmax(Dmin, Dmax,Jt);
Gmin = calcGmin(Dmin, Dmax, Lmin, Lmax, Jh);

dx = ipcCeil((Zmax2-Gmin)/2.0, padSizeRoundOff);
dpos = ipcRound(Zmax2/2.0-dx/2.0, padPlaceRoundOff);

pinNumber = nD + 1;
offset = (pitch*(nE-1))/2;
beginSmd(dx, dy);
	orientation(0);
	for (k = 0; k < nE; k++) {
		sprintf(pinName, "%d", pinNumber);
		name(pinName);
		position(dpos, ipcRound(-offset+k*pitch,padPlaceRoundOff));
		pinNumber++;
	}
	pinNumber = pinNumber + nD;
	orientation(180);
	for (k = 0; k < nE; k++) {
		sprintf(pinName, "%d", pinNumber);
		name(pinName);
		position(-dpos, ipcRound(offset-k*pitch,padPlaceRoundOff));
		pinNumber++;
	}
end();

sprintf(pinName, "%d", pinNumber);
generateExposedPad(pinName, 0, 0);

// Draw Legend
real clearance = getLibraryParameterValueReal("legendClearance");
real legendLineWidth = getLibraryParameterValueReal("legendLineWidth");
real legendRoundOff = getLibraryParameterValueReal("legendRoundOff");

real cX = ipcCeil(D1max/2 + legendLineWidth/2, legendRoundOff);
real cY = ipcCeil(E1max/2 + legendLineWidth/2, legendRoundOff);
real p1X = ipcCeil((pitch*(nD-1))/2 + Xmax/2 + clearance + legendLineWidth/2, legendRoundOff);
real p1Y = ipcCeil((pitch*(nE-1))/2 + Xmax/2 + clearance + legendLineWidth/2, legendRoundOff);
real p11Y = ipcFloor(Zmax/2-legendLineWidth/2, legendRoundOff);

beginLegendOutline(LAYER_TPLACE);
	position(-cX, p1Y);
	position(-cX, cY);
	position(-p1X, cY);
end();

beginLegendOutline(LAYER_TPLACE);
	position(p1X, cY);
	position(cX, cY);
	position(cX, p1Y);
end();

beginLegendOutline(LAYER_TPLACE);
	position(cX, -p1Y);
	position(cX, -cY);
	position(p1X, -cY);
end();

beginLegendOutline(LAYER_TPLACE);
	position(-p1X, -p11Y);
	position(-p1X, -cY);
	position(-cX, -cY);
	position(-cX, -p1Y);
end();

setLayer(LAYER_TNAMES);
changeSize(getLibraryParameterValueReal("legendFontHeight"));
changeRatio(getLibraryParameterValueReal("legendFontRatio"));
changeAlign("CENTER");
changeFont("VECTOR");
begin("TEXT");
	name(">Name");
	position(0,0);
end();

// Draw Courtyard

real courtyardExcess = strtod(lookup(tableContent, index, "CourtyardExcess"));
real courtyardRoundOff = strtod(lookup(tableContent, index, "CourtyardRoundOff"));
real courtyardLineWidth = getLibraryParameterValueReal("courtyardLineWidth");

real cE = ipcCeil((Zmax + 2*courtyardExcess - courtyardLineWidth)/2, courtyardRoundOff);
real cD = ipcCeil((Zmax2 + 2*courtyardExcess - courtyardLineWidth)/2, courtyardRoundOff);

real cE1 = ipcCeil(max((E1max + 2*courtyardExcess - courtyardLineWidth)/2, cY + legendLineWidth/2 - courtyardLineWidth/2), courtyardRoundOff);
real cD1 = ipcCeil(max((D1max + 2*courtyardExcess - courtyardLineWidth)/2, cX + legendLineWidth/2 - courtyardLineWidth/2), courtyardRoundOff);

real cE2 = ipcCeil((ipcRound(pitch*(nE-1),padPlaceRoundOff) + dy + 2*courtyardExcess - courtyardLineWidth)/2, courtyardRoundOff);
real cD2 = ipcCeil((ipcRound(pitch*(nD-1),padPlaceRoundOff) + dy + 2*courtyardExcess - courtyardLineWidth)/2, courtyardRoundOff);

beginCourtyard(LAYER_TKEEPOUT);
	position(-cD2,cE);
	position(cD2,cE1);
	position(cD1,cE2);
	position(cD,-cE2);
	position(cD1,-cE1);
	position(cD2,-cE);
	position(-max(cD2, ipcCeil(p1X + legendLineWidth/2 - courtyardLineWidth/2, courtyardRoundOff)),-cE1);
	position(-cD1, -cE2);
	position(-cD, cE2);
	position(-cD1,cE1);
	position(-cD2,cE);
end();

// Draw Component Outline
cX = D1max/2.0;
cY = E1max/2.0;

beginComponentOutline(LAYER_TDOCU);
	position(-cX,cY);
	position(cX,cY);
	position(cX,-cY);
	position(-cX,-cY);
	position(-cX,cY);
end();

begin("RECT");
	for (k=0; k < nD; k++) {
		position(((k-(nD-1)/2.0)*pitch) - bmax/2, -(Emax/2 - Lmax));
		position(((k-(nD-1)/2.0)*pitch) + bmax/2, -Emax/2);
		
		
		position(((k-(nD-1)/2.0)*pitch) - bmax/2, Emax/2 - Lmax);
		position(((k-(nD-1)/2.0)*pitch) + bmax/2, Emax/2);
	}
	
	for (k=0; k < nE; k++) {
		position(-(Dmax/2 - Lmax),((k-(nE-1)/2.0)*pitch) - bmax/2);
		position(-Dmax/2,((k-(nE-1)/2.0)*pitch) + bmax/2);
		
		position((Dmax/2 - Lmax),((k-(nE-1)/2.0)*pitch) - bmax/2);
		position(Dmax/2,((k-(nE-1)/2.0)*pitch) + bmax/2);
	}
	
end();

real componentLineWidth = getLibraryParameterValueReal("componentLineWidth");
begin("CIRCLE");
	lineWidth(componentLineWidth);
	position(-cX + 0.2*min(cX,cY), -cY + 0.2*min(cX,cY));
	position(-cX + 0.2*min(cX,cY), -cY + 0.2*min(cX,cY) + componentLineWidth/2);
end();

changeSize(getLibraryParameterValueReal("componentFontHeight"));
changeAlign("CENTER");
changeFont("PROPORTIONAL");
begin("TEXT");
	name(">Name");
	position(0,0);
end();



sprintf(packageDescription, "<b>Quad Flat Package (%d pins, %.2fmm pitch)</b> <i>%s Material Condition</i><br>Body (LxWxH): %.2fmm x %.2fmm x %.2fmm<br>Lead (L): %.2fmm<br>", int(nD*2+nE*2), pitch, materialConditionLongStr[materialCondition], D1min+(D1max-D1min)/2, E1min+(E1max-E1min)/2, Amin+(Amax-Amin)/2, Lmin+(Lmax-Lmin)/2);
sprintf(packageName, "QFP%dP%d_%dX%dX%dL%dX%dT0X0%s_%dX%dX%dL%dX%d", 
	int(nD*2+nE*2), int(round(pitch*100)), int(round((Dmin+(Dmax-Dmin)/2)*100)), int(round((Emin+(Emax-Emin)/2)*100)), int(round((Amin+(Amax-Amin)/2)*100)), int(round((Lmin+(Lmax-Lmin)/2)*100)), int(round((bmin+(bmax-bmin)/2)*100)), materialConditionStr[materialCondition],
	int(round((Dmax-Dmin)/2*100)), int(round((Emax-Emin)/2*100)), int(round((Amax-Amin)/2*100)), int(round((Lmax-Lmin)/2*100)), int(round((bmax-bmin)/2*100)));
	
exitWizard();
