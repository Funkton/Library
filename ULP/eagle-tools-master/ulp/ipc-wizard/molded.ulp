//MOLDED	Molded Components, 2-Pins	Resistor, Capactor, Inductor, Diode
//<p>This will allow you to generate Molded Components like Resistors, Capacitors Inductors or Diodes.</p><\br><center><img width=256 src="ipc-wizard/capm-01.png"></center>

#include "common.h"

//Wizard Description
wizardName = "MOLDED";
wizardDescription = "<img src=\"capm-02.png\">";
wizardImage = "capm-01.png";

// ComboBox Parameter
int k=0;
string familyNames[];
familyNames[k++] = "Resistor";
familyNames[k++] = "Capacitor";
familyNames[k++] = "Capacitor, Polarized";
familyNames[k++] = "Inductor";
familyNames[k++] = "Diode";
familyNames[k++] = "LED";
familyNames[k++] = "Fuse";
int isPolarized[] = {0, 0, 1, 0, 1, 1, 0};
int isAnodeCatode[] = {0, 0, 0, 0, 1, 1, 0};
string namingPrefix[] = {"RESM", "CAPM", "CAPMP", "INDM", "DIOM", "LEDM", "FUSM"};
string materialConditionStr[] = {"L","N","M"};
string materialConditionLongStr[] = {"Least","Nominal","Most"};

// UI Parameter Elements
addParameterComboBox("family", "Family", strjoin(familyNames,'|'), 1);

addParameterHeader("Body Dimensions");
	addParameterMinMax("A","Height (A)", 0, 0);
	addParameterMinMax("D","Length (D)", 0, 0);
	addParameterMinMax("E","Width (E)", 0, 0);
	

addParameterHeader("Terminal Dimensions");
	addParameterMinMax("L","Length (L)", 0, 0);
	addParameterMinMax("b","Width (b)", 0, 0);
	
int debugRet = 0;

runWizard();

int family = getParameterListBox("family");
int materialCondition = getParameterListBox("materialCondition");

real Hmin = getParameterMin("A");
real Hmax = getParameterMax("A");

real Lmin = getParameterMin("D");
real Lmax = getParameterMax("D");

real Wmin = getParameterMin("b");
real Wmax = getParameterMax("b");

real Tmin = getParameterMin("L");
real Tmax = getParameterMax("L");

real W2min = getParameterMin("E");
real W2max = getParameterMax("E");

string lengthCode = "HMAX";
real length = Lmin + (Lmax - Lmin)/2.0;
real height = Hmin + (Hmax - Hmin)/2.0;
height = Hmax;
if (Hmax <= 4.20) lengthCode = "H420";
if (Hmax <= 3.20) lengthCode = "H320";
if (Hmax <= 2.20) lengthCode = "H220";
if (Hmax <= 1.20) lengthCode = "H120";




string index = lengthCode + materialConditionStr[materialCondition];

string path = filedir(argv[0]);
string tableContent[];
fileread(tableContent, path + "/molded.data");
real Jt = strtod(lookup(tableContent, index, "Jtoe"));
real Jh = strtod(lookup(tableContent, index, "Jheel"));
real Js = strtod(lookup(tableContent, index, "Jside"));

// Draw Pads
real Zmax = calcZmax(Lmin, Lmax, Jh);
real Gmin = calcGmin(Lmin, Lmax, Tmin, Tmax, Jt);
real Xmax = calcXmax(Wmin, Wmax, Js);

real padSizeRoundOff = getLibraryParameterValueReal("padSizeRoundOff");
real padPlaceRoundOff = getLibraryParameterValueReal("padPlaceRoundOff");

real dx = ipcCeil((Zmax-Gmin)/2.0, padSizeRoundOff);
real dy = ipcCeil(Xmax,padSizeRoundOff);
real xPos = ipcRound(Zmax/2.0-dx/2.0, padPlaceRoundOff);

beginSmd(dx, dy);
	if (isAnodeCatode[family]) {
		name("C");
	} else {
		name("1");
	}
	position(-xPos,0);
	if (isAnodeCatode[family]) {
		name("A");
	} else {
		name("2");
	}
	position(xPos,0);
end();

// Draw Legend
real clearance = getLibraryParameterValueReal("legendClearance");
real legendLineWidth = getLibraryParameterValueReal("legendLineWidth");
real legendRoundOff = getLibraryParameterValueReal("legendRoundOff");

real lx = Gmin/2-clearance-legendLineWidth/2;
real ly = W2max/2+legendLineWidth/2;
lx = ipcCeil(lx, legendRoundOff);
ly = ipcCeil(ly, legendRoundOff);

if (W2max >= (Xmax+clearance+legendLineWidth)) {
	lx = Lmax/2-legendLineWidth/2;
	lx = ipcFloor(lx, legendRoundOff);
	ly = ipcCeil(ly, legendRoundOff);
}

real lx2 = lx;

if (isPolarized[family]) {
	lx = Zmax/2 + clearance + legendLineWidth/2;
	lx2 = Lmax/2-legendLineWidth/2;
	ly = max(Xmax/2 + clearance,W2max/2) + legendLineWidth/2;
	ly = ipcCeil(ly, legendRoundOff);
	lx = ipcCeil(lx, legendRoundOff);
	lx2 = ipcCeil(lx2, legendRoundOff);
	beginLegendOutline(LAYER_TPLACE);
		position(-lx, ly);
		position(-lx, -ly);
	end();
}


beginLegendOutline(LAYER_TPLACE);
	position(-lx, ly);
	position(lx2, ly);
end();
beginLegendOutline(LAYER_TPLACE);
	position(-lx, -ly);
	position(lx2, -ly);
end();

setLayer(LAYER_TNAMES);
changeSize(getLibraryParameterValueReal("legendFontHeight"));
changeRatio(getLibraryParameterValueReal("legendFontRatio"));
changeAlign("CENTER");
changeFont("VECTOR");
begin("TEXT");
	name(">Name");
	position(0,0);
end();

// Draw Courtyard
real CourtyardExcess = strtod(lookup(tableContent, index, "CourtyardExcess"));
real CourtyardRoundOff = strtod(lookup(tableContent, index, "CourtyardRoundOff"));
real courtyardLineWidth = getLibraryParameterValueReal("courtyardLineWidth");
real cyX = ipcCeil(max(max(Zmax,Lmax)/2.0+CourtyardExcess, lx + legendLineWidth/2)-courtyardLineWidth/2, CourtyardRoundOff);
real cyX2 = ipcCeil(max(max(Zmax,Lmax)/2.0+CourtyardExcess, lx2 + legendLineWidth/2)-courtyardLineWidth/2, CourtyardRoundOff);
real cyY = ipcCeil(max(max(Xmax,W2max)/2.0+CourtyardExcess, ly + legendLineWidth/2)-courtyardLineWidth/2, CourtyardRoundOff);

beginCourtyard(LAYER_TKEEPOUT);
	position(-cyX,cyY);
	position(cyX2,-cyY);
	position(-cyX,cyY);
end();


// Draw Component Outline
real cX = Lmax/2.0;
real cY = W2max/2.0;
real tW = Tmax;
beginComponentOutline(LAYER_TDOCU);
	position(-cX,cY);
	position(cX,cY);
	position(cX,-cY);
	position(-cX,-cY);
	position(-cX,cY);
end();

real componentLineWidth = getLibraryParameterValueReal("componentLineWidth");
begin("CIRCLE");
	lineWidth(componentLineWidth);
	position(-(cX-tW) + 0.2*min(cX-tW,cY), -cY + 0.2*min(cX-tW,cY));
	position(-(cX-tW) + 0.2*min(cX-tW,cY), -cY + 0.2*min(cX-tW,cY) + componentLineWidth/2);
end();

cY = Wmax/2.0;
begin("RECT");
	position(-cX,cY);
	position(-cX+tW,-cY);
end();
begin("RECT");
	position(cX,cY);
	position(cX-tW,-cY);
end();



changeSize(getLibraryParameterValueReal("componentFontHeight"));
changeAlign("CENTER");
changeFont("PROPORTIONAL");
begin("TEXT");
	name(">Name");
	position(0,0);
end();

sprintf(packageDescription, "<b>%s, Molded </b><i>%s Material Condition</i><br>Body (LxWxH): %.2fmm x %.2fmm x %.2fmm<br>Lead (LxW): %.2fmm x %.2fmm<br>", familyNames[family],materialConditionLongStr[materialCondition], Lmin+(Lmax-Lmin)/2, W2min+(W2max-W2min)/2, Hmin+(Hmax-Hmin)/2, Tmin+(Tmax-Tmin)/2, Wmin+(Wmax-Wmin)/2);
sprintf(packageName, "%s%dX%dX%dL%dX%d%s_%dX%dX%dL%dX%d", 
	namingPrefix[family], int(round((Lmin+(Lmax-Lmin)/2)*100)), int(round((W2min+(W2max-W2min)/2)*100)), int(round((Hmin+(Hmax-Hmin)/2)*100)), int(round((Tmin+(Tmax-Tmin)/2)*100)),int(round((Wmin+(Wmax-Wmin)/2)*100)), materialConditionStr[materialCondition],
	int(round((Lmax-Lmin)/2*100)), int(round((W2max-W2min)/2*100)), int(round((Hmax-Hmin)/2*100)), int(round((Tmax-Tmin)/2*100)), int(round((Wmax-Wmin)/2*100)));

exitWizard();
