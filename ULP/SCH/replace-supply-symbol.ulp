#usage "en:<b>Export of libraries from a drawing.</b><p>\n"
          "This can be used to make individual changes to components in a project. "
          "Just load schematic, board or both, use this ULP to generate one or several libraries "
          "containing the used components. Make your changes in the library/libraries and use the "
          "UPDATE command to introduce the changes to schematic and/or board.<p>"
          "See Help for further details.<p>"

#require 6.0301

//-----------------------------------------------------------------------------

string Version = "1.01";
string Status = "";
string SymbolName = "GND";
string ReplaceName = "GND";
int LibNameIndex = 0;
int ScriptExec   = 1;   // execute script automatically after generating
string strFileName;

string LibNames[] = {
    "supply.lbr"
    };

//------------ main ----------------------------------------

if (!schematic)
{
  dlgMessageBox("Please start from schematic editor!");
  exit(1);
}
else
{
    schematic(SCH)
    {
        strFileName = filesetext(SCH.name, "_ReplaceLibParts.scr");
        
        int Result = dlgDialog("Replace Power Supply Symbol")
        {
            dlgGroup("Replace Power Symbol - v"+Version) {
                dlgGridLayout {
                    dlgCell(0, 0) dlgLabel("Replace with symbol from:");
                    dlgCell(0, 1) dlgComboBox(LibNames, LibNameIndex);
                    dlgCell(1, 0) dlgLabel("Symbol name to replace:");
                    dlgCell(1, 1)  dlgStringEdit(SymbolName);
                    dlgCell(2, 0) dlgLabel("Replace symbol name with:");
                    dlgCell(2, 1)  dlgStringEdit(ReplaceName);
                }
            }
                
            dlgLabel(Status, 1);
            
            dlgHBoxLayout {
                dlgCheckBox("&Execute Script", ScriptExec);
                dlgStretch(1);
                dlgPushButton("+&" + "OK") dlgAccept();
                dlgPushButton("-&" + "Cancel") dlgReject();
            }
        };
    
        if (!Result)
        {
            exit(0);
        }
        else
        {        
            output(strFileName, "wtD")
            {
                printf("# '%s;\n\n", EAGLE_SIGNATURE);
                printf("SET UNDO_LOG OFF;\n");
                printf("# Migrate parts to '%s'\n", LibNames[LibNameIndex]);
        
                SCH.sheets(S)
                {
                    printf("#\n# SHEET %d - MIGRATE PARTS\n#\n", S.number);
                    printf("EDIT .s%d\n", S.number);
        
                    S.parts(P)
                    {
                        if ((P.device.name == SymbolName))  // && (P.device.package == ""))
                        {
                            printf("REPLACE %s %s;\n", P.name, ReplaceName);
                        }
                    }
                }
                printf("SET UNDO_LOG ON;\n");
        		printf("# Put all libraries back into use. REMOVED!! I DO NOT WANT LIBRARIES NOT IN DESIGN TO BE USED. \n");
            }
            
            if (ScriptExec)
                exit ("SCRIPT '" + strFileName + "';");
            else
                exit(0);
        }
    }
};
