#usage "<b>Show airwires and parts selected by group command in schematic</b><p>"
	"Ease partitial place and route of functional blocks.<p>"
	"Use 'RATSNEST *' at the command line in board to show all airwires.<br>"
	"Use 'RATSNEST ! *' at the command line in board to show no airwires.<p>"
	"<author>peter@seng.de</author>";

string cmd;

if (schematic)
{
	int cntN = 0;
	int cntP = 0; 
//	output("_cmd.txt", "wt")	
//	{
		schematic(S)
		{	
			cmd = "edit .brd; RATS ! *; RATS "; // create command string
			S.sheets(SH) // work-around for bug in EAGLE 5/6 --> must use sheet context, see http://www.element14.com/community/thread/16119
				SH.nets(N)
				{
					if (ingroup(N))
					{
						cmd += N.name + " "; // add netname to command string
						++cntN;
//						printf("%s\n", cmd);
					}
				}
		}

		cmd += "; SHOW "; // add show command to command string
//		printf("%s\n", cmd);
	
		schematic(M)
		{
	
			M.sheets(SH) // work-around for bug in EAGLE 5/6 --> must use sheet context, see http://www.element14.com/community/thread/16119
			if (ingroup(SH))
			{
				SH.instances(I) // work-around for bug in EAGLE 5/6 --> must use instances context, see http://www.element14.com/community/thread/16119
					if (ingroup(I))
					{
						cmd += I.name + " "; // add partname to command string
						++cntP;
//						printf("%s\n", cmd);
					}
			}
		}
//	}

	if ((!cntN) && (!cntP))
	{
		dlgMessageBox("Define group in schematic first, no nets or parts selected", "OK");
		exit(0);
	}
	exit(cmd);

}
else
{
	dlgMessageBox("ULP must be run from schematic", "OK");    
	exit(0);
}
