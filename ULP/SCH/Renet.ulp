string add_text = "_1";
string cmd = "";

schematic(S) {
S.sheets(SH) {
SH.nets(N) {
N.segments(SEG) {
SEG.wires(W) {
sprintf(cmd, "%s NAME %s%s (%f %f); ",cmd, N.name, add_text,
u2inch(W.x1), u2inch(W.x2));
}
}
}
}
}
dlgMessageBox(cmd);

exit(cmd);
