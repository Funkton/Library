/*
Title : CFGTOGGLE.ulp
Purpose : Toggles config value retreived from eaglerc.
Author : Cameron Nicks

License : Creative Commons Attribution-ShareAlike 4.0 International
        : CC BY-SA 4.0
        : https://creativecommons.org/licenses/by-sa/4.0/

*******************************************************************************
*				Copyright (c) 2017 Cameron Nicks                              *
*******************************************************************************
THIS SOFTWARE IS PROVIDED BY THE AUTHOR ``AS IS'' AND ANY EXPRESS OR IMPLIED
WARRANTIES, INCLUDING, BUT NOT LIMITED TO, THE IMPLIED WARRANTIES OF
MERCHANTABILITY AND FITNESS FOR A PARTICULAR PURPOSE ARE DISCLAIMED. IN NO
EVENT SHALL THE AUTHOR BE LIABLE FOR ANY DIRECT, INDIRECT, INCIDENTAL,
SPECIAL, EXEMPLARY, OR CONSEQUENTIAL DAMAGES (INCLUDING, BUT NOT LIMITED TO,
PROCUREMENT OF SUBSTITUTE GOODS OR SERVICES; LOSS OF USE, DATA, OR PROFITS;
OR BUSINESS INTERRUPTION) HOWEVER CAUSED AND ON ANY THEORY OF LIABILITY,
WHETHER IN CONTRACT, STRICT LIABILITY, OR TORT (INCLUDING NEGLIGENCE OR
OTHERWISE) ARISING IN ANY WAY OUT OF THE USE OF THIS SOFTWARE, EVEN IF
ADVISED OF THE POSSIBILITY OF SUCH DAMAGE.



Version:
0.2 06/13/17
	- Added repeat mode. --t argument toggles last used. Can keep single shortcut key for toggle, and change which to set to it using menu or other shortcuts.
	- Debug Mode. --d argument must be used after --t or other argument.

0.1 06/12/17
	- Initial Proof of concept. Only works with Eagle default configurations
	

Ideas:
- Add handling of non binary eaglerc set commands (ie: ON|OFF, WALKAROUND|IGNORE)
[ ] : Add ability to handle multiple setting toggles at a time.
[0.2] - Save last used setting name and setup flag for toggle shortcut. Can assign one shortcut to repeat the last used setting.
[ ]	: --h History window popup dialog. Add last used cfg locations and display in dialog for selection.

Notes:
cfgset can be used to set display option values in eaglerc, but SET must be used in order to refresh the display.

*/

#usage 	"en: Toggle Eagle Configuration Setting.<br>Call this ulp with the setting name to be toggled as the argument.<p>"
		"Works on any binary setting located in eaglerc.usr. See Eagle help.<p>\n"
		"Example: RUN CFGTOGGLE.ulp Option.SignalNamesOnPads<br>\n"
		"Will toggle the setting <b>Display the Signal Names On Pads</b> option located in <i>Options -> Set... -> Misc</i><br>\n"
		"Can set to run from shortcuts or menu items to enable quick toggling.<hr><p>\n"
		"<i>Arguments</i><br>--t : Toggle last used<br>--d : Debug<p>\n"
		"<hr><author>Author: Cameron Nicks</author><br>\n"
		"<author>Cameron.Nicks+Layout@gmail.com</author><br>"
		"<author>cnicks@phaseivengr.com</author>"

string VERSION = "0.2 (13-Jun-2017)";
int debug = 0;


string cmdType = "SET";
string cfgPrefix = "EAGLE:";//This is used to add EAGLE: to the beginning of the parameter name to call using cfgget.


//If run without arguments, show usage info and exit.
if (argc == 1) {
	  dlgMessageBox(usage);
	  exit(1);
}
else {

	  string SettingName = "";
	  string cfgToGet = "";
	  string SettingVal = "";
	  string ToggleVal = "";
	  
	if (argv[2] == "--d") {
	debug = 1;
	}
	
	// ----- Set the name to retrieve -----//
	if (argv[1] == "--t"){ //Repeat last
		SettingName = cfgget("cfgtoggle.lastused"); if (debug) {dlgMessageBox ("Set from last used");} //Debug
		
	}	else { // Use argument as name
		SettingName = argv[1]; if (debug) {dlgMessageBox ("Set from argument");} //Debug
	}
	
	
	// Has the prefix been defined
	if (cfgPrefix){
		sprintf (cfgToGet, "%s%s", cfgPrefix, SettingName); //if (debug) {dlgMessageBox ("Prefixed name");} //Debug
		
	}	else {
		sprintf (cfgToGet, "%s", SettingName); //if (debug) {dlgMessageBox ("ULP setting");} //Debug
	}
	// -----------------------------------//
	
	// ----- Get current setting from eaglerc -----//
	SettingVal = cfgget(cfgToGet);
	
		if (debug) {
			string dbg = "";
			sprintf(dbg, "%s = %s", cfgToGet, SettingVal);
			dlgMessageBox (dbg);
			} //Debug

		//Toggle Function. 
		if (SettingVal == "0"){
			ToggleVal = "1";
		}	else {
			ToggleVal ="0";
		}
		// --
			
		// Save last used values to eaglerc.usr
		cfgset("cfgtoggle.lastused", SettingName);
		
		// Construct output command
		string cmd = "";
		sprintf(cmd, "%s %s %s;\n", cmdType, SettingName, ToggleVal);
		
			if (debug) {
				string dbg = "";
				sprintf(dbg, "Command: %s", cmd);
				dlgMessageBox (dbg);
				} //Debug
		

		// Print to the statusbar
		string result = "";
		sprintf(result, "%s has been set to: %s", SettingName, ToggleVal); 
		//dlgMessageBox(result);
		status(result); //Can this stay on the statusbar? Right now it says ulp finished.

	exit(cmd);
	}
