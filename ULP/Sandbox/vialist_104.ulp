// via list in window with:
// start, end, position, drill, signal name
//
// Generated by Andres Restrepo - 29.07.2013




int WindowMinWidth      = 600;

string DatabaseFilename;

numeric string ViaLines[];          /* Via table variable      */
numeric string TypeLines[];         /* Via type table variable */
string ViaType[];

int    nViaCount,nTypeCount;        /* Via and via type number  */
int    ViaStart[],ViaEnd[];         /* Via start and end layers */
int    ViaX[],ViaY[];               /* Via coordinates          */ 
int    ViaDrill[];                  /* Via drill                */
int    ViaDiam [];                  /* Via diameter             */
int    ViaVisit[];                  /* Via visit flag           */
int    ViaTypeCount[];              /* Via type counter         */

string ViaName[];
string Filename;

int    Selected = 0;
int    Sort = 0;
real   Zoom=10;
int    user_units;





string HelpTextEN =
  "<b>List of Vias</b>"
  "<ul>"
  "<li>List all vias with all its information.</li><p>"
  "<li>Double-click on one VIA and it will "
  "highlight the corresponding signal and put the VIA in the center of the window</li><p>"
  "<\ul>"  
  ;

string ULPname = "Via-List v";
string Release = "1.06";
string ReleaseDate = "Ago 22, 2013";  // ars662001@yahoo.com


string HistoryText2 =
  "<p>"
  "The following is a history of this program (most recent first)."
  "<p>"
  "Version History"
  "<ul>"
  "<li>v1.06 - show same the dimension as actual user settings</li><p>"
  "<li>v1.05 - selectable zoom.</li><p>"
  "<li>v1.04 - add table  with via types and counter for each of them.</li><p>"
  "<li>v1.03 - tabbed format.</li><p>"
  "<li>v1.02 - menu format.</li><p>"
  "<li>v1.01 - only file output.</li><p>"  
  "<li>v1.00 - Initial release version. - Andres Restrepo S.</li><p>"
  "</ul>"
;


void DisplayHelp(void)
{
    dlgDialog("Via list - Help")
    {
        dlgHBoxLayout dlgSpacing(650);
        dlgHBoxLayout
        {
            dlgVBoxLayout dlgSpacing(300);
            dlgTextView(HelpTextEN);
        }
        dlgHBoxLayout
        {
            dlgStretch(1);
            dlgPushButton("-Close") dlgReject();
        }
    };
}





void CollectData(void)
{
nViaCount=0;

if (board)
  board(B) {
    Filename=B.name;
    user_units=B.grid.unit;
    B.signals(S) { 
      S.vias(V)   { 
        ViaStart[nViaCount]=V.start;
        ViaEnd  [nViaCount]=V.end;
        ViaX    [nViaCount]=V.x;
        ViaY    [nViaCount]=V.y;
        ViaDrill[nViaCount]=V.drill;
        ViaDiam [nViaCount]=V.diameter[1];
        ViaName [nViaCount]=S.name;

        ViaVisit[nViaCount]=0;
        nViaCount++;      
      }    
    }    
  }
}

void GenerateList(void)
{
  int NumLines   = 1;  
  string StrIndex   ;
  string StrViaType ;
  string StrX    ;
  string StrY    ;
  string StrViaDrill;
  string StrUnits;
          
  if(user_units==GRID_UNIT_MIC)      StrUnits="[mic]";
  else if(user_units==GRID_UNIT_MM)  StrUnits="[mm]";
  else if(user_units==GRID_UNIT_MIL) StrUnits="[mil]";
  else                               StrUnits="[inch]";
 
  // Header:       
  sprintf(ViaLines[0],"Index\tType\tX %s\tY %s\tDrill [mm]\tSignal\t",StrUnits,StrUnits);
  // Lines:
  for (int i = 0; i < nViaCount; i ++)
  {
    if(nViaCount<100)         sprintf (StrIndex   , "%02d" , i);
    else if(nViaCount<1000)   sprintf (StrIndex   , "%03d" , i);
    else if(nViaCount<10000)  sprintf (StrIndex   , "%04d" , i);
    else if(nViaCount<100000) sprintf (StrIndex   , "%05d" , i);
    sprintf (StrViaType , "%02d-%02d" , ViaStart[i],ViaEnd[i]);    
    if(user_units==GRID_UNIT_MIC)      
    {
      sprintf (StrX, "%8.2f", u2mic(ViaX[i]));    
      sprintf (StrY, "%8.2f", u2mic(ViaY[i]));
    }
    else if(user_units==GRID_UNIT_MM)  
    {
      sprintf (StrX, "%8.2f", u2mm(ViaX[i]));    
      sprintf (StrY, "%8.2f", u2mm(ViaY[i]));
    }
    else if(user_units==GRID_UNIT_MIL) 
    {
      sprintf (StrX, "%8.2f", u2mil(ViaX[i]));    
      sprintf (StrY, "%8.2f", u2mil(ViaY[i]));
    }
    else  
    {
      sprintf (StrX   , "%8.2f", u2inch(ViaX[i]));    
      sprintf (StrY   , "%8.2f", u2inch(ViaY[i]));
    }
    sprintf (StrViaDrill, "%5.3f", u2mm(ViaDrill[i]));
  
    
    ViaLines[NumLines] = StrIndex + "\t" + StrViaType + "\t" + StrX + "\t" + StrY + "\t"  + StrViaDrill + "\t" + ViaName[i] + "\t";
    NumLines ++;
  }
  ViaLines[NumLines] = "";
}


void ScanViaTypes(void)
{
int    NumLines   = 1; 
int    found;
string StrViaType; 
string StrViaTypeCnt;

        
  nTypeCount=0;
  for (int i=0; i < nViaCount; i++)  // ---- scan all vias -----------------
  {
    sprintf (StrViaType , "%02d-%02d" , ViaStart[i],ViaEnd[i]);  
       
    found=-1;
    for (int j=0; j < nTypeCount; j++) // ---- scan all via type vector -----------------
    {
      if(ViaType[j]==StrViaType)
      {
        found=j;
        break;
      } 
    }  // END ---- scan all via type vector --------- END --------          

    if(found==-1)
    {      
      ViaType     [nTypeCount]=StrViaType;      
      ViaTypeCount[nTypeCount]=1;              
      nTypeCount++;          
    }
    else    
    {
       ViaTypeCount[found]++;        
    }

  }  // END ---- scan all vias ----------------- END ----------
}



void GenerateTypeList(void)
{
int NumLines   = 1; 
string StrViaTypeCnt;

  // Header:
  TypeLines[0] = "Type" + "\t" + "Number";

  for (int j = 0; j < nTypeCount; j ++)
  {
    sprintf (StrViaTypeCnt, "%03d" , ViaTypeCount[j]);
    TypeLines[NumLines]=ViaType[j] + "\t" + StrViaTypeCnt;
    NumLines++;
  }
  TypeLines[NumLines] = "";
}



void save(void)
{
  int i;
  string StrIndex   ;
  string StrViaType;
  string StrViaX    ;
  string StrViaY    ;
  string StrViaDrill;
  string StrViaDiam;
  

  output(filesetext(Filename, ".VIA3")) {
    printf("       VIA List\n");
    printf("i    start-end      (X Y)        drill  diameter signal name\n");
    printf("                    [mil]        [mm]   [mm]\n");
    for (int i = 0; i < nViaCount; i ++)
    {
      if(nViaCount<100)         { sprintf (StrIndex   , "%02d" , i); }
      else if(nViaCount<1000)   { sprintf (StrIndex   , "%03d" , i); }
      else if(nViaCount<10000)  { sprintf (StrIndex   , "%04d" , i); }
      else if(nViaCount<100000) { sprintf (StrIndex   , "%05d" , i); }
      sprintf (StrViaType , "%02d-%02d" , ViaStart[i],ViaEnd[i]);    
      sprintf (StrViaX    , "%8.2f", u2mil(ViaX[i]));
      sprintf (StrViaY    , "%8.2f", u2mil(ViaY[i]));
      sprintf (StrViaDrill, "%5.3f", u2mm(ViaDrill[i]));
      sprintf (StrViaDiam , "%5.3f", u2mm(ViaDiam [i]));
    
      printf("[%s] %s (%s %s) %s  %s - %s\n",
              StrIndex, StrViaType, StrViaX,StrViaY, StrViaDrill,StrViaDiam,ViaName[i]);     
    } 
    printf("\nNumber of vias:%d\n", i);
  }
}


// execute a command at exit:
void show(int sel) { 
string cmd;
real x,y;
 
  sel--;
  if(user_units==GRID_UNIT_MIC)      { x=u2mic(ViaX[sel]);  y=u2mic(ViaY[sel]); }
  else if(user_units==GRID_UNIT_MM)  { x=u2mm(ViaX[sel]);   y=u2mm(ViaY[sel]);  }  
  else if(user_units==GRID_UNIT_MIL) { x=u2mil(ViaX[sel]);  y=u2mil(ViaY[sel]);  }   
  else                               { x=u2inch(ViaX[sel]); y=u2inch(ViaY[sel]);  }   
  sprintf(cmd, "WINDOW FIT; WINDOW %f; WINDOW (%f %f); SHOW '%s'", Zoom,x,y,ViaName[sel] );
  exit(cmd);
}



void AppDialog()
{
string strnvias;

    sprintf(strnvias,"[Total vias=%d]",nViaCount);
    int rtn = dlgDialog(ULPname +  Release)
    {
        // Set the default view width
        dlgHBoxLayout dlgSpacing(WindowMinWidth);
                   
        dlgHBoxLayout
        {
            dlgLabel("Vias (Double-click on selected VIA)" + strnvias);
            dlgLabel(DatabaseFilename, 1);
            dlgStretch(1);            
            dlgPushButton("H&elp") DisplayHelp();
        }

        dlgHBoxLayout
        {            
            dlgVBoxLayout dlgSpacing(500);
            dlgListView("", ViaLines, Selected, Sort) show(Selected) ;
        }
            
        dlgHBoxLayout
        {            
            dlgStretch(5);
            
            dlgHBoxLayout {
              dlgStretch(1);
              dlgPushButton("Save")   save();         
              dlgPushButton("+OK")    dlgAccept();
              dlgPushButton("Cancel") dlgReject();
            }
        }
    };
    
    if(!rtn) exit(0);
}



int hor;


/* Main: */

string strnvias;

if (!board)
{
  dlgMessageBox("You should run this ULP from an open board design.");
  exit(-1);
}


void main(void)
{
real kiki;

CollectData  ();
ScanViaTypes    ();

GenerateList    ();
GenerateTypeList();


     
  sprintf(strnvias,"<li>[Total vias = %d]</li><li>[Total via types = %d]<\li>",nViaCount,nTypeCount);

  dlgDialog(ULPname  + Release) {
 

  dlgTabWidget {
    dlgTabPage("Processing") {

      dlgHBoxLayout  {
        
        dlgGroup("Via examiner") {
                
          dlgVBoxLayout { 
                             
          
          dlgGroup("Parameters") {
            dlgSpacing(8);
            dlgGridLayout {
              dlgCell( 1, 0)  dlgLabel("Show Zoom");
              dlgCell( 1, 1)  dlgRealEdit(Zoom, 0.5, 30);
                                         
              //dlgCell( 2, 0)  dlgLabel("Teardrop Curve Factor  ");      //ars662001@yahoo.com
              //dlgCell( 2, 1)  dlgRealEdit(kiki, 0.5, 5.0); //ars662001@yahoo.com             
              
              //dlgCell( 3, 0)  dlgLabel("Ignore all segments >= ");
              //dlgCell( 3, 1)  dlgRealEdit(kiki, 4.0, 400.0);
              //dlgCell( 3, 2)  dlgLabel(" mils");

              //dlgCell( 4, 0)  dlgLabel("Ignore all segments/drill ratios >= ");
              //dlgCell( 4, 1)  dlgRealEdit(kiki, 0.1, 99.0);
            }
            }
              // unit selector:   
//            dlgHBoxLayout  {
//              dlgGroup("X,Y") {
//               dlgRadioButton("&mils" ,hor );//GenerateList(0,0));       
//               dlgRadioButton("&mm"  , hor);
//              }
//              dlgGroup("Drills") {
//                dlgRadioButton("&mils", hor);
//                dlgRadioButton("&mm"  , hor);
//              }
//            }

            //dlgLabel(strnvias);                     
            //{
            //  dlgSpacing(8);
            //  dlgLabel("Double-Click on via to select :");
            //  dlgListView("", Lines, Selected, Sort) show(Selected) ;
            //}
            //dlgLabel(strnvias);

            // via list:    
            dlgLabel("Double-Click on via to select :");           
            dlgHBoxLayout          
            {
              dlgVBoxLayout dlgSpacing(100);    
              dlgListView("", TypeLines, Selected) ; //show(Selected) ;
            }

            // via list:    
            dlgLabel("Double-Click on via to select :");           
            dlgHBoxLayout          
            {
              dlgVBoxLayout dlgSpacing(400);    
              dlgListView("", ViaLines, Selected, Sort) show(Selected) ;
            }
          }
          dlgStretch(1);
          dlgSpacing(10);
          dlgHBoxLayout {
            dlgPushButton("Save")   save();         
            dlgPushButton("+OK")    dlgAccept();
            dlgPushButton("Cancel") dlgReject();
          }
        }
      
        //dlgTextView(mainscrtext);
        dlgTextView(strnvias);
        }
      }
      

      dlgTabPage("Overview") {
        dlgTextView(HelpTextEN);
      }

      dlgTabPage("History") {
        dlgTextView(Release + " " + ReleaseDate + " " + HistoryText2);       
      }
    } // tab page
  };

}
