/*
	C.Nicks edited version
	
	This ulp is going to turn into a layer color manager essentially.
	It will list the layers in a selection field, on the side will include information. Palette number, fill number, color display, color hex, and Opacity (alpha %)
	Fills can be displayed by making icons (advanced feature?)
	Color should be % instead of byte values, makes more sense.
	- Show highlight color next to main color as well.
	- Ability to change alpha/colors relatively (decrease alpha by 50%, which would work on highlight as well)
	
	Still buggy when setting colors. Wrong palette is being set.
	I think it has to do with the bit masking and shifting.
	
	Wish list:
	- Retreive alpha from layer. DONE
	- Display layer number (dlgListView)
	- Change alpha int to spinBox percentage (opacity)
	- Run from command line (as Usage states)
	- Selection settings area to side. Show layer color, palette number, and have table background show initial color, then opacity % (alpha -> 0-100)
	- Use checkbox to include only used layers or all.
	- Undo (store original colors that were changed in usr file)
	- CHANGE LAYER to last selected layer in listbox.
	- Hex display/entry for rgb. recalculates when changing each rgb box.
	- Alpha presets, Solid, medium, light, extra light.
*/

#usage "run setalpha 1 90\n"
"to set the alpha value of whatever color layer 1 is using to 90\n"


string UsedLayers[]  = { "NONE" };
int    usedLayerN[] = { 0 };
int    colorN[];
int    nAlpha = 212;
int    cnt = 0;
int    Selected = 0;
int    setLayer = 0;
int		 cAlpha = 0; //Alpha layer is currently set to
int		cColor = 0; // Current Color value
int	debug = 1;

int red, green, blue;
//enum {alpha, red, green, blue}; // Set byte names for split function. Call function and request which byte to return. Useful for repeated calls for r g b edit boxes.

//----- LAYER FUNCTIONS -----

string LayerNames[];
  //Names (plus numbers in brackets) of all available (used) layers
int LayerNumbers[];
int LayerColors[];
  //Numbers of all available (used) schematics layers
int LayerNumber=0;
  //Available (used) layers counter
int LayerVisible[];
  //1 for each layer that is currently visible (0 otherwise)
int InvalidLayers[]={91,92,93};
  //Layers in which NO graphics should be placed (nets, busses, pins)
int InvalidLayerNr=3;
  //Invalid layers count
	string IntToStr(int x) {
  //Returns the integer X formatted as string
  string Text;
  sprintf(Text,"%d",x);
  return Text;
  }

int MemoriseLayer(UL_LAYER L,int Index) {
  //Writes name and number of the LAYER into the position INDEX of the global
  //arrays LAYERNAMES and LAYERNUMBERS. Returns the next unused index of the
  //arrays
  int Nr,LayerValid = 1;
  //Check, whether the layer is one of the unsupported layers
  for (Nr=0; Nr<InvalidLayerNr; Nr++)
    if (L.number == InvalidLayers[Nr])
      LayerValid = 0;
  //If not, and the layer is visible, add it to the layer collection
  if (LayerValid == 1) {
    LayerNames[Index] += 	IntToStr(L.number)+"  " + L.name;
    LayerNumbers[Index] = L.number;	
		LayerColors[Index] = L.color;
    Index++;
    }
  return Index;
  }

void CollectLayers(void) {
  //Collects all currently used layers and writes their names and numbers
  //into the global variables LAYERNAMES and LAYERNUMBERS
	
  board(B)
    B.layers(L) {
      //Check, whether the layer is visible or not
      if ((L.used) && (L.visible))
        LayerVisible[L.number]=1;
      else
        LayerVisible[L.number]=0;
      //Memorise the used layer's name and number for dialog display
			if (L.used){
				LayerNumber = MemoriseLayer(L,LayerNumber);
				
				usedLayerN[cnt] = L.number;
				UsedLayers[cnt]  = L.name;
				colorN[cnt]     = L.color;
				++cnt;
			}
    }
  }
	
	//Todo:
	// Write color handling functions to split into hex bytes (aa rr gg bb)
	
int getColor (int LayerNumber){
	// Get the alpha value for layer.
	int color;
	
	if (board) board(B) {
		B.layers(L) {
			if (L.number == LayerNumber){
				color = (palette(L.color));
			}
		}
	}
	if (debug){	dlgMessageBox ("getColor Returns: Layer = " + IntToStr(LayerNumber) + " Color:" + IntToStr(color));}
	return color;
}
	
int getAlpha (int LayerNumber){
	// Get the alpha value for layer.
	int result;
	int color;
	int alpha;
	
	if (board) board(B) {
		B.layers(L) {
			if (L.number == LayerNumber){
				color = (palette(L.color)); // >> 24  ^ 0xFFFFFF00 // BUG: For some reason reading in 0x40 (50), returns -156
			}
		}
	}
	// Get alpha byte (0xaarrggbb)
	alpha = (color >> 24) & 0xFF;
	result = alpha;
	
		if (debug){	dlgMessageBox ("getAlpha Returns: " + IntToStr(result));	}
	return result;
}

void splitColor (int color) { //Feed this the 4byte color (0xaarrggbb)
	red = (color >> 16) & 0xff;
	green = (color >> 8) & 0xff;
	blue = color & 0xff;
	
	string s;
	sprintf(s, "splitColor: red= 0x%02X, green= 0x%02X, blue= 0x%02X", red, green, blue);
	if (debug) dlgMessageBox(s, "OK");
	}


	
int menue(void) {
	
string LayerLabel;
//nAlpha = getAlpha (LayerNumbers[Selected]);
cColor = getColor (1);
splitColor(cColor);

  dlgDialog("Set Layer Alpha") {
    dlgGroup("Layer Alpha") {
			dlgLabel(LayerLabel, 1);
      dlgVBoxLayout {
        dlgLabel("&Layer");
        dlgListBox(LayerNames, Selected) {
					if (dlgSelectionChanged()){
						nAlpha = getAlpha (LayerNumbers[Selected]);
						LayerLabel = LayerNames[Selected];
						//dlgRedisplay();
					}
				};
      }
      dlgVBoxLayout {
        dlgLabel("Alpha");
        dlgIntEdit(nAlpha, 0, 255); // Bug: If alpha is below 100, this box reads 0
      }
    }

    dlgHBoxLayout {
      dlgPushButton("+OK") {
        setLayer = (LayerNumbers[Selected] -1); // Why is this grabbing the wrong layer number?
				if (debug){
					string temp;
					sprintf(temp, "Layer: %d, is set to color: %d", setLayer, LayerColors[setLayer]);
					dlgMessageBox(temp);
					}
        dlgAccept();
        return 1;
      }
      dlgStretch(1);
      dlgPushButton("-&Cancel") { dlgReject(); exit (0);}
    }
  };
  return 0;
}


if (board) board(B) {
	//Memorise layer names, numbers and visibility
  CollectLayers();

/*
  B.layers(L) {
    usedLayerN[cnt] = L.number;
    UsedLayers[cnt]  = L.name;
    colorN[cnt]     = L.color;
    ++cnt;
  }
*/
	
	nAlpha = getAlpha (LayerNumbers[Selected]);

  if (menue()) {
    int color = (palette(colorN[setLayer]) & 0x00FFFFFF) | (nAlpha << 24);
    string s;
    sprintf(s, "SET PALETTE %d 0x%08X;", colorN[setLayer], color);
  if (debug) dlgMessageBox(s, "OK");
    exit(s);
  }

} else {
  dlgMessageBox("Run this ULP from a Board", "OK");
  exit (0);
}
