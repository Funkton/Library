#usage "<b>Generate Package CAE (Aluminium Electrolytic Capacitor)</b><p>\n"
"(Copyright 2006) by Weartronics, T. Mühlke, C. Mädiger."


string package_name = "CAPAE530X540N";
int dlgresult;

real pad_x = 1.6;
real pad_y = 3.0;
real pad_space = 4.5;
real keepout_x = 8.5;
real keepout_y = 6.3;
real silkscreen_x = 5.3;
real silkscreen_y = 5.3;

real component_s = 1.55;
real component_t = 2.2;
real component_w = 0.65;
real component_ab = 5.3;
real component_h = 5.4;

string Picture = "<img src=cae.bmp>";
	
dlgresult = dlgDialog("Insert CAE Package Data") 
	{
	dlgStretch(0);
	dlgHBoxLayout 
	dlgLabel(Picture);
  dlgGroup("Eagle Package Data")
		{
		dlgGridLayout 
			{
			dlgCell(1, 0) dlgLabel("Name");	
			dlgCell(1, 1) dlgStringEdit(package_name)
			dlgCell(2, 0) dlgSpacing(100);
			}
    }
	dlgGroup("IPC-7351 Land Pattern and Statistics")
		{
		dlgGridLayout 
			{
			dlgCell(1, 0) dlgLabel("Pad X");
			dlgCell(1, 1) dlgRealEdit(pad_x,0.0,99.0);
			dlgCell(2, 0) dlgLabel("Pad Y");
			dlgCell(2, 1) dlgRealEdit(pad_y,0.0,99.0);	
			dlgCell(3, 0) dlgLabel("Pad Space C");
			dlgCell(3, 1) dlgRealEdit(pad_space,0.0,99.0);	
			dlgCell(4, 0) dlgLabel("Curtyard V1");
			dlgCell(4, 1) dlgRealEdit(keepout_x,0.0,99.0);	
			dlgCell(5, 0) dlgLabel("Curtyard V2");
			dlgCell(5, 1) dlgRealEdit(keepout_y,0.0,99.0);	
			dlgCell(6, 0) dlgLabel("Silkscreen R1");
			dlgCell(6, 1) dlgRealEdit(silkscreen_x,0.0,99.0);	
			dlgCell(7, 0) dlgLabel("Silkscreen R2");
			dlgCell(7, 1) dlgRealEdit(silkscreen_y,0.0,99.0);	
			dlgCell(8, 0) dlgSpacing(100);
			}
		}
	dlgGroup("IPC-7351 Component")
		{
		dlgGridLayout 
			{
			dlgCell(1, 0) dlgLabel("Component *S");
			dlgCell(1, 1) dlgRealEdit(component_s);	
			dlgCell(2, 0) dlgLabel("Component *T");
			dlgCell(2, 1) dlgRealEdit(component_t);	
			dlgCell(3, 0) dlgLabel("Component W");
			dlgCell(3, 1) dlgRealEdit(component_w);	
			dlgCell(4, 0) dlgLabel("Component A/B");
			dlgCell(4, 1) dlgRealEdit(component_ab);	
			dlgCell(5, 0) dlgLabel("Component H");
			dlgCell(5, 1) dlgRealEdit(component_h);	
			dlgCell(6, 0) dlgSpacing(100);
			}
		}
	dlgPushButton("-Cancel") dlgReject();	
	dlgPushButton("+Ok") dlgAccept();
	};

if(dlgresult != 1)
	exit(EXIT_FAILURE);

if(package != 1)
	exit(EXIT_FAILURE);


real _LINE_WIDTH = 0.127;
real _CLEARANCE = 0.254;
real _TEXT_SIZE = 0.8128;
int _TEXT_RATIO = 10;

string result = "";
string buffer = "";

void concat()
{
	string strings[] = {result, buffer};
	result = strjoin(strings, ' ');
}

sprintf(buffer, "GRID mm;"); concat();
sprintf(buffer, "SET WIRE_BEND 2;"); concat();
sprintf(buffer, "CHANGE FONT vector;"); concat();
sprintf(buffer, "CHANGE SIZE %f;", _TEXT_SIZE); concat();
sprintf(buffer, "CHANGE RATIO %d;", _TEXT_RATIO); concat();

sprintf(buffer, "EDIT %s.pac;", package_name); concat();
sprintf(buffer, "DESCRIPTION '<b>%s</b><p>\nIPC-7351 Standart';", strupr(package_name)); concat();

sprintf(buffer, "LAYER Top;"); concat();
sprintf(buffer, "SMD %f %f -0 R90 '+' (-%f 0);", pad_x, pad_y, pad_space/2); concat();
sprintf(buffer, "SMD %f %f -0 R90 '-' (%f 0);", pad_x, pad_y, pad_space/2); concat();

sprintf(buffer, "LAYER tKeepout;"); concat();
sprintf(buffer, "WIRE 0 (-%f -%f) (-%f %f) (%f %f) (%f -%f) (-%f -%f);", keepout_x/2, keepout_y/2, keepout_x/2, keepout_y/2, keepout_x/2, keepout_y/2, keepout_x/2, keepout_y/2, keepout_x/2, keepout_y/2); concat();

sprintf(buffer, "LAYER tPlace;"); concat();

if(silkscreen_y/2 - silkscreen_y*0.25 > pad_x/2 + _CLEARANCE + _LINE_WIDTH/2)
{
	sprintf(buffer, "WIRE %f (-%f %f) (-%f %f) (-%f %f) (%f %f) (%f %f);", _LINE_WIDTH, silkscreen_x/2, pad_x/2 + _CLEARANCE + _LINE_WIDTH/2, silkscreen_x/2, silkscreen_y/2 - silkscreen_y*0.25, silkscreen_x/2 - silkscreen_x*0.25, silkscreen_y/2, silkscreen_x/2, silkscreen_y/2, silkscreen_x/2, pad_x/2 + _CLEARANCE + _LINE_WIDTH/2); concat();
	sprintf(buffer, "WIRE %f (-%f -%f) (-%f -%f) (-%f -%f) (%f -%f) (%f -%f);", _LINE_WIDTH, silkscreen_x/2, pad_x/2 + _CLEARANCE + _LINE_WIDTH/2, silkscreen_x/2, silkscreen_y/2 - silkscreen_y*0.25, silkscreen_x/2 - silkscreen_x*0.25, silkscreen_y/2, silkscreen_x/2, silkscreen_y/2, silkscreen_x/2, pad_x/2 + _CLEARANCE + _LINE_WIDTH/2); concat();
	sprintf(buffer, "CIRCLE 0 (-%f %f) (-%f %f);", silkscreen_x/2 + _CLEARANCE + _LINE_WIDTH/2 + 0.25, pad_x/2 + _CLEARANCE + 0.25, silkscreen_x/2 + _CLEARANCE + _LINE_WIDTH/2, pad_x/2 + _CLEARANCE + 0.25); concat();
}
else
{
	real shortfall = (pad_x/2 + _CLEARANCE + _LINE_WIDTH/2) - (silkscreen_y/2 - silkscreen_y*0.25);
	sprintf(buffer, "WIRE %f (-%f %f) (-%f %f) (%f %f) (%f %f);", _LINE_WIDTH, silkscreen_x/2 - shortfall, silkscreen_y/2 - silkscreen_y*0.25 + shortfall, silkscreen_x/2 - silkscreen_x*0.25, silkscreen_y/2, silkscreen_x/2, silkscreen_y/2, silkscreen_x/2, pad_x/2 + _CLEARANCE + _LINE_WIDTH/2); concat();
	sprintf(buffer, "WIRE %f (-%f -%f) (-%f -%f) (%f -%f) (%f -%f);", _LINE_WIDTH, silkscreen_x/2 - shortfall, silkscreen_y/2 - silkscreen_y*0.25 + shortfall, silkscreen_x/2 - silkscreen_x*0.25, silkscreen_y/2, silkscreen_x/2, silkscreen_y/2, silkscreen_x/2, pad_x/2 + _CLEARANCE + _LINE_WIDTH/2); concat();
	sprintf(buffer, "CIRCLE 0 (-%f %f) (-%f %f);", silkscreen_x/2 - shortfall + _CLEARANCE + _LINE_WIDTH/2 + 0.25, pad_x/2 + _CLEARANCE + 0.25, silkscreen_x/2 - shortfall + _CLEARANCE + _LINE_WIDTH/2, pad_x/2 + _CLEARANCE + 0.25); concat();
}

sprintf(buffer, "LAYER tDocu;"); concat();
sprintf(buffer, "WIRE %f (-%f -%f) (-%f %f) (-%f %f) (%f %f) (%f -%f) (-%f -%f) (-%f -%f);", _LINE_WIDTH, component_ab/2, component_ab/2 - component_ab*0.25, component_ab/2, component_ab/2 - component_ab*0.25, component_ab/2 - component_ab*0.25, component_ab/2, component_ab/2, component_ab/2, component_ab/2, component_ab/2, component_ab/2 - component_ab*0.25, component_ab/2, component_ab/2, component_ab/2 - component_ab*0.25); concat();
sprintf(buffer, "CIRCLE %f (0 0) (%f 0);", _LINE_WIDTH, component_ab/2 - _CLEARANCE - _LINE_WIDTH); concat();
sprintf(buffer, "RECT (-%f -%f) (-%f %f);", (component_s + component_t*2)/2, component_w/2, component_s/2, component_w/2); concat();
sprintf(buffer, "RECT (%f -%f) (%f %f);", (component_s + component_t*2)/2, component_w/2, component_s/2, component_w/2); concat();

sprintf(buffer, "LAYER tNames;"); concat();
sprintf(buffer, "TEXT '>NAME' (-%f %f);", silkscreen_x/2 + _LINE_WIDTH/2, silkscreen_y/2 + _LINE_WIDTH/2 + _CLEARANCE); concat();

sprintf(buffer, "LAYER tValues;"); concat();
sprintf(buffer, "TEXT '>VALUE' (-%f -%f);", silkscreen_x/2 + _LINE_WIDTH/2, silkscreen_y/2 + _LINE_WIDTH/2 + _CLEARANCE + _TEXT_SIZE); concat();

sprintf(buffer, "WINDOW fit;"); concat();

exit(result);
