#usage "<b>Generate Package MLD (Molded Body)</b><p>\n"
"(Copyright 2006) by Weartronics, T. Mühlke, C. Mädiger."


string package_name = "DIOM5226X203N";
int dlgresult;

real pad_x = 1.55;
real pad_y = 2.4;
real pad_space = 4.2;
real keepout_x = 7.1;
real keepout_y = 3.5;
real silkscreen_x = 5.6;
real silkscreen_y = 3.0;

real component_l = 5.2;
real component_t = 1.175;
real component_tw = 1.45;
real component_w = 2.6;
real component_h = 2.03;
string component_type = "D";
int component_type_value = 2;
	
string Picture = "<img src=mld.bmp>";

dlgresult = dlgDialog("Insert MLD Package Data") 
	{
	dlgStretch(0);
	dlgHBoxLayout
	dlgLabel(Picture); 
	dlgGroup("Eagle Package Data")
		{
		dlgGridLayout 
			{
			dlgCell(1, 0) dlgLabel("Name");	
			dlgCell(1, 1) dlgStringEdit(package_name)
			dlgCell(2, 0) dlgSpacing(100);
			}
		}
	dlgGroup("IPC-7351 Land Pattern and Statistics")
		{
		dlgGridLayout 
			{
			dlgCell(1, 0) dlgLabel("Pad X");
			dlgCell(1, 1) dlgRealEdit(pad_x,0.0,99.0);
			dlgCell(2, 0) dlgLabel("Pad Y");
			dlgCell(2, 1) dlgRealEdit(pad_y,0.0,99.0);	
			dlgCell(3, 0) dlgLabel("Pad Space C");
			dlgCell(3, 1) dlgRealEdit(pad_space,0.0,99.0);	
			dlgCell(4, 0) dlgLabel("Curtyard V1");
			dlgCell(4, 1) dlgRealEdit(keepout_x,0.0,99.0);	
			dlgCell(5, 0) dlgLabel("Curtyard V2");
			dlgCell(5, 1) dlgRealEdit(keepout_y,0.0,99.0);	
			dlgCell(6, 0) dlgLabel("Silkscreen R1");
			dlgCell(6, 1) dlgRealEdit(silkscreen_x,0.0,99.0);	
			dlgCell(7, 0) dlgLabel("Silkscreen R2");
			dlgCell(7, 1) dlgRealEdit(silkscreen_y,0.0,99.0);	
			dlgCell(8, 0) dlgSpacing(100);
			}
		}
	dlgGroup("IPC-7351 Component")
		{
		dlgGridLayout 
			{
			dlgCell(1, 0) dlgSpacing(100);
			dlgCell(2, 0) dlgLabel("Component L");
			dlgCell(2, 1) dlgRealEdit(component_l);	
			dlgCell(3, 0) dlgLabel("Component T");
			dlgCell(3, 1) dlgRealEdit(component_t);	
			dlgCell(4, 0) dlgLabel("Component TW");
			dlgCell(4, 1) dlgRealEdit(component_tw);	
			dlgCell(5, 0) dlgLabel("Component W");
			dlgCell(5, 1) dlgRealEdit(component_w);	
			dlgCell(6, 0) dlgLabel("Component H");
			dlgCell(6, 1) dlgRealEdit(component_h);	
			dlgCell(7, 0) dlgSpacing(100);
			}
		dlgSpacing(10);
		dlgGroup("Component type")
			{
			dlgGridLayout
				{
				dlgCell(1, 0) dlgRadioButton("L", component_type_value);
		 	 	dlgCell(1, 1)	dlgRadioButton("C", component_type_value);
				dlgCell(1, 2)	dlgRadioButton("D", component_type_value);
				}
			}		
		}
	dlgPushButton("-Cancel") dlgReject();	
	dlgPushButton("+Ok") dlgAccept();
	};

if(dlgresult != 1)
	exit(EXIT_FAILURE);

switch (component_type_value)
	{
	case 0: component_type="L"; break;
	case 1: component_type="C"; break;
	case 2: component_type="D"; break;
	default: exit(EXIT_FAILURE);
	}
	
if(package != 1)
	exit(EXIT_FAILURE);

real _LINE_WIDTH = 0.127;
real _CLEARANCE = 0.254;
real _TEXT_SIZE = 0.8128;
int _TEXT_RATIO = 10;

if(component_type != "L" && component_type != "C" && component_type != "D")
	exit(EXIT_FAILURE);

string result = "";
string buffer = "";

void concat()
{
	string strings[] = {result, buffer};
	result = strjoin(strings, ' ');
}

sprintf(buffer, "GRID mm;"); concat();
sprintf(buffer, "SET WIRE_BEND 2;"); concat();
sprintf(buffer, "CHANGE FONT vector;"); concat();
sprintf(buffer, "CHANGE SIZE %f;", _TEXT_SIZE); concat();
sprintf(buffer, "CHANGE RATIO %d;", _TEXT_RATIO); concat();

sprintf(buffer, "EDIT %s.pac;", package_name); concat();
sprintf(buffer, "DESCRIPTION '<b>%s</b><p>\nIPC-7351 Standart';", strupr(package_name)); concat();

sprintf(buffer, "LAYER Top;"); concat();

if(component_type == "L")
{
	sprintf(buffer, "SMD %f %f -0 R90 '1' (-%f 0);", pad_x, pad_y, pad_space/2); concat();
	sprintf(buffer, "SMD %f %f -0 R90 '2' (%f 0);", pad_x, pad_y, pad_space/2); concat();
}
else if(component_type == "C")
{
	sprintf(buffer, "SMD %f %f -0 R90 '+' (-%f 0);", pad_x, pad_y, pad_space/2); concat();
	sprintf(buffer, "SMD %f %f -0 R90 '-' (%f 0);", pad_x, pad_y, pad_space/2); concat();
}
else if(component_type == "D")
{
	sprintf(buffer, "SMD %f %f -0 R90 'K' (-%f 0);", pad_x, pad_y, pad_space/2); concat();
	sprintf(buffer, "SMD %f %f -0 R90 'A' (%f 0);", pad_x, pad_y, pad_space/2); concat();
}

sprintf(buffer, "LAYER tKeepout;"); concat();
sprintf(buffer, "WIRE 0 (-%f -%f) (-%f %f) (%f %f) (%f -%f) (-%f -%f);", keepout_x/2, keepout_y/2, keepout_x/2, keepout_y/2, keepout_x/2, keepout_y/2, keepout_x/2, keepout_y/2, keepout_x/2, keepout_y/2); concat();

sprintf(buffer, "LAYER tPlace;"); concat();
sprintf(buffer, "CIRCLE 0 (-%f %f) (-%f %f);", silkscreen_x/2 + _CLEARANCE + _LINE_WIDTH/2 + 0.25, pad_x/2 + _CLEARANCE + 0.25, silkscreen_x/2 + _CLEARANCE + _LINE_WIDTH/2, pad_x/2 + _CLEARANCE + 0.25); concat();

if(silkscreen_y/2 >= pad_x/2 + _CLEARANCE + _LINE_WIDTH/2)
{
	sprintf(buffer, "WIRE %f (-%f %f) (-%f %f) (%f %f) (%f %f);", _LINE_WIDTH, silkscreen_x/2, pad_x/2 + _CLEARANCE + _LINE_WIDTH/2, silkscreen_x/2, silkscreen_y/2, silkscreen_x/2, silkscreen_y/2, silkscreen_x/2, pad_x/2 + _CLEARANCE + _LINE_WIDTH/2); concat();
	sprintf(buffer, "WIRE %f (-%f -%f) (-%f -%f) (%f -%f) (%f -%f);", _LINE_WIDTH, silkscreen_x/2, pad_x/2 + _CLEARANCE + _LINE_WIDTH/2, silkscreen_x/2, silkscreen_y/2, silkscreen_x/2, silkscreen_y/2, silkscreen_x/2, pad_x/2 + _CLEARANCE + _LINE_WIDTH/2); concat();
}
else
{
	sprintf(buffer, "WIRE %f (-%f %f) (%f %f);", _LINE_WIDTH, silkscreen_x/2, silkscreen_y/2, silkscreen_x/2, silkscreen_y/2); concat();
	sprintf(buffer, "WIRE %f (-%f -%f) (%f -%f);", _LINE_WIDTH, silkscreen_x/2, silkscreen_y/2, silkscreen_x/2, silkscreen_y/2); concat();
}

sprintf(buffer, "LAYER tDocu;"); concat();
sprintf(buffer, "WIRE %f (-%f -%f) (-%f %f) (%f %f) (%f -%f) (-%f -%f);", _LINE_WIDTH, component_l/2, component_w/2, component_l/2, component_w/2, component_l/2, component_w/2, component_l/2, component_w/2, component_l/2, component_w/2); concat();
sprintf(buffer, "RECT (-%f -%f) (-%f %f);", component_l/2 + _LINE_WIDTH*1.5, component_tw/2, component_l/2 + _LINE_WIDTH*0.5, component_tw/2); concat();
sprintf(buffer, "RECT (%f -%f) (%f %f);", component_l/2 + _LINE_WIDTH*1.5, component_tw/2, component_l/2 + _LINE_WIDTH*0.5, component_tw/2); concat();

if(component_type == "L")
{
}
else if(component_type == "C")
{
	sprintf(buffer, "WIRE %f (-%f %f) (-%f -%f);", _LINE_WIDTH, component_l/2 - component_l*0.2, component_w/2, component_l/2 - component_l*0.2, component_w/2); concat();
}
else if(component_type == "D")
{
	sprintf(buffer, "RECT (-%f %f) (-%f -%f);", component_l/2, component_w/2, component_l/2 - component_l*0.2, component_w/2); concat();
}

sprintf(buffer, "LAYER tNames;"); concat();
sprintf(buffer, "TEXT '>NAME' (-%f %f);", silkscreen_x/2 + _LINE_WIDTH/2, silkscreen_y/2 + _LINE_WIDTH/2 + _CLEARANCE); concat();

sprintf(buffer, "LAYER tValues;"); concat();
sprintf(buffer, "TEXT '>VALUE' (-%f -%f);", silkscreen_x/2 + _LINE_WIDTH/2, silkscreen_y/2 + _LINE_WIDTH/2 + _CLEARANCE + _TEXT_SIZE); concat();

sprintf(buffer, "WINDOW fit;"); concat();

exit(result);
