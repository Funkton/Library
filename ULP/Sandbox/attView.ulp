/*
Title : attView.ulp
Purpose : Easy viewer of all parts' attributes
Author : Cameron Nicks
Link: https://goo.gl/Gh9nsG

License : Creative Commons Attribution-ShareAlike 4.0 International
        : CC BY-SA 4.0
        : https://creativecommons.org/licenses/by-sa/4.0/

*******************************************************************************
*				Copyright (c) 2017 Cameron Nicks                              *
*******************************************************************************
THIS SOFTWARE IS PROVIDED BY THE AUTHOR ``AS IS'' AND ANY EXPRESS OR IMPLIED
WARRANTIES, INCLUDING, BUT NOT LIMITED TO, THE IMPLIED WARRANTIES OF
MERCHANTABILITY AND FITNESS FOR A PARTICULAR PURPOSE ARE DISCLAIMED. IN NO
EVENT SHALL THE AUTHOR BE LIABLE FOR ANY DIRECT, INDIRECT, INCIDENTAL,
SPECIAL, EXEMPLARY, OR CONSEQUENTIAL DAMAGES (INCLUDING, BUT NOT LIMITED TO,
PROCUREMENT OF SUBSTITUTE GOODS OR SERVICES; LOSS OF USE, DATA, OR PROFITS;
OR BUSINESS INTERRUPTION) HOWEVER CAUSED AND ON ANY THEORY OF LIABILITY,
WHETHER IN CONTRACT, STRICT LIABILITY, OR TORT (INCLUDING NEGLIGENCE OR
OTHERWISE) ARISING IN ANY WAY OUT OF THE USE OF THIS SOFTWARE, EVEN IF
ADVISED OF THE POSSIBILITY OF SUCH DAMAGE.



Version:
0.3 MM/DD/YY
	- Show attributes list without selecting

0.2 09/05/17
	- Added library name label for selected part
	- Added direct goo.gl link
	
0.1 09/05/17
	- Basic proof of concept editor dialog

	
BUGS:
- Pressing ENTER when selection is in attributes list has return error.
- No extensive testing done yet
- Modules have not been tested
- Design blocks have not been tested

To-Do:
- Add in ATT-COPY functions

Feature Wish List:
- Edit in library button (open device).
- Dialog edit box to manually type in part name (change selected part to this box)
- More ignore handling features (libraries, attributes, ?)
- Copy and paste function
	^- Checkboxes to select which get copied
- Context entries to open with part selected.

Advanced:
- Ability to edit directly from dialog instead of calling native ATTRIBUTE
	^- Apply button to make changes and recall ulp
- Save changes into library (back annotate changes)

*/

#usage 	"en: <b>attView.ulp</b> - Attribute Viewer."
		"<hr><b>Usage:</b>"
		"<br>RUN attView"
		"<br>RUN attView <i>utility</i>"		
		"<p><b>Utiliy:</b>"
		/*"<b><i>--install</i></b> : Installs the utility to the board context menus.<br>\n"*/
		"<br><b><i>help</i></b> : Shows this usage information."
		"<br><b><i>--version</i></b> : Shows the version number of the ULP being called."
		"<br><b><i>--locate-ulp</i></b> : Shows the location of the ULP being called (Useful for debug)."
		"<p><b>Limitations:</b>"
		"<br>- Pressing ENTER when selection is in attributes list has return error."
		"<br>- Module handling has not been tested."
		"<br>- Design Blocks handling has not been tested."
		"<p><b>Known Bugs:</b>"
		"<br>- Please submit to author"
		"<p><hr> Cameron Nicks: https://goo.gl/y1y1zn <br>"
		"<author>Author: Cameron.Nicks+Layout@gmail.com</author><br>"
		"<author>Author: cnicks@phaseivengr.com</author>"

string VERSION = "0.3 Sandbox";

// ------ SETTINGS -------
int debug = 0;
int Selected = 0;
// ------------------------

// ------ VARIBLES -------
string attList[];
string attValues[];
string combinedList[];
numeric string partsList[];
string cmd;
//string attList; // Attributes list
int cnt; //counter to use outside of function
// ------------------------

// ------ OPTIONS ---------
 //If run without arguments, show usage info and exit. To-do: build dialog window
if (argv[1] == "help") {
		dlgMessageBox(usage);
		exit(1);
}
if (argv[1] == "--version"){
	 string tmp = "ULP Version: " + VERSION;
	 dlgMessageBox(tmp);
	 exit(0);
}
if (argv[1] == "--locate-ulp"){
	 dlgMessageBox(argv[0]);
	 exit(0);
}
// ------------------------


// ------ FUNCTIONS -------

// getParts function: Build list of parts to display from design files
void getParts(){
	// Beginning Schematic
	if (schematic){
		schematic(S){
			int i;
			S.parts(P){
				if (P.device.library != "Supply"){ //ignore libraries
					partsList[i] = P.name;
					i++;
				}
			}
			string tmp;
			sprintf(tmp, "%d", i);
			//dlgMessageBox ("There are " + tmp + " parts");
		}
	}
	if (board){
		board(B){
			int i;
			B.elements(E){
				if (E.package.library != "Frames" && E.package.library != "Logo") { // Ignore parts from these libraries
					partsList[i] = E.name;
					i++;
				}
			}
			
			string tmp;
			sprintf(tmp, "%d", i);
			//dlgMessageBox ("There are " + tmp + " parts");
		}
	}
}
// End getParts function:

// getAtt function: retreive attributes for selected part
void getAtt(string s){
	int i = 0;
	string attListView[];
	string attInfo;
	
	if (schematic){
		schematic(S){
			S.parts(P){
				P.instances(I){
					if (P.name == s) {
						P.attributes(A) {
							//sprintf(attInfo, "%\t%s")
							attListView[i] = A.name + "\t" + A.value;
							combinedList[i] = attListView[i];
							i++;
						}
					}
					combinedList[i] = "\0"; //terminate the array to clear off old ones
				}
			}
		}
	}
	if (board){
		board(B){
			B.elements(E){
					if (E.name == s) {
						E.attributes(A) {
							if (A.name != "NAME"){
							attListView[i] = A.name + "\t" + A.value;
							combinedList[i] = attListView[i];
							i++;
							}
						}
					}
					combinedList[i] = "\0"; //terminate the array to clear off old ones
			}
		}
	}
	
}
// End getAtt function

// getLib function: retreive library name for selected part. Send part name, recieve library name
string getLib(string s){
	string libName;
	
	if (schematic){
		schematic(S){
			S.parts(P){
				if (P.name == s){
					libName = P.device.library;
				}
			}
		}
		return libName;
	}
	if (board){
		board(B){
			B.elements(E){
				if (E.name == s){
					libName = E.package.library;
				}
			}
		}
		return libName;
	}
	else {
		string error;
		sprintf(error, "getLib error looking up %s", s);
		dlgMessageBox (error);
	exit(0);
	}
}
// End getLib function

// locatePart function. Return edit command to switch to the sheet the part is located on (sch only)
	string locatePart (string lookupPart) {
		string sheetNum;
		project.schematic(S){
			S.parts(P){
				P.instances(I) {
					if (P.name == lookupPart) {
						if (debug) {
							string tmp;
							sprintf(tmp, "%s is on sheet: %d", lookupPart, I.sheet);
							dlgMessageBox (tmp);
						}
					sprintf (sheetNum, "EDIT .s%d; ", I.sheet);
					return sheetNum;
					}
				}
			}
		}
	}
// End locatePart function

// editAtt function: returns command to edit the attributes of selected part
string editAtt (string s){
string Result;

	// If there is a schematic available, switch to sheet with destination part. Editing attributes from brd vs sch act a bit differently
	if (project.schematic){
		cmd += locatePart(s);
	}

	sprintf(Result, "ATTRIBUTE %s", s);
	
	cmd += Result;
		if (debug) {
			dlgMessageBox (cmd);
		}
	return cmd;
}
// End editAtt function
// ------------------------

// ------ ULP -------------

// Get the part names
getParts();
getAtt(partsList[Selected]);

// ------ DIALOG -------------
//int Result = 
dlgDialog("Attributes List") {
string partName;
string libraryName;

int AttSelected = -1;

	dlgVBoxLayout {
	//dlgLabel("Select Part to View Attributes");
	
		dlgGroup("View Attributes"){
			dlgGridLayout {

			dlgCell(0, 0)	dlgLabel("Selected Part:");
			dlgCell(0, 1)	{dlgLabel(partName, 1); dlgStretch (1);};
			
			
			//dlgCell(0, 0, 0, 1) dlgLabel("Select Part to View Attributes");

			dlgCell(1, 0, 1, 1)	dlgListBox(partsList, Selected) {
					if (dlgSelectionChanged()){
						partName = partsList[Selected];
						getAtt(partsList[Selected]);
						libraryName = getLib(partsList[Selected]);
					}
				};
			dlgCell(2, 0) dlgPushButton("-Close") dlgReject();
				
			dlgCell(0, 2)	dlgLabel("Library:");
			dlgCell(0, 3)	{dlgLabel(libraryName, 1); dlgStretch (1);};
			dlgCell(0, 4)	dlgSpacing(200);
				
			dlgCell(1, 2, 1, 4)	dlgListView("Attribute\tValue", combinedList, AttSelected);
			dlgCell(2, 2)	dlgPushButton("+Edit") exit(editAtt(partsList[Selected]));
				
					

			//dlgPushButton("+OK") getAtt(partsList[Selected]);
			}
		}
	}
};
	//getAtt(partsList[Selected]);
//dlgMessageBox("last selected\n" + attList[Selected]);
//if (Result == 0) exit (0);
